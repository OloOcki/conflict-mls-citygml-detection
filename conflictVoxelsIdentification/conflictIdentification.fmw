FME workspace conflictIdentification.fmw

Parameters:
- SourceDataset_CITYGML = D:\projects\PassageFinder\data\raw\CityGML\TUM Munich\TUM Munich.gml   # Source CityGML File(s)
- DestDataset_LAS = D:\projects\PassageFinder\Octomap\octomapChangeDetection\data\processed\detectedConflictsBld23   # Destination ASPRS LAS Folder
- SourceDataset_PCD_6 = D:\projects\PassageFinder\PCDtoWGS84\data\processed\inUTMlocalOctomap\bld23\mlsFree.pcd   # Point Cloud Data File(s)
- SourceDataset_PCD_8 = D:\projects\PassageFinder\PCDtoWGS84\data\processed\inUTMlocalOctomap\bld23\mlsOccupied.pcd   # Point Cloud Data File(s)
- bldSelect = DEBY_LOD2_4959323   # Select building ID
- GR = 2   # Accuracy of CityGML generalization
- clGR = 90   # Confidence Level for CityGML generalization
- clCityGML = 90   # Confidence Level for CityGML global accuracy
- eCityGML = 0.04   # Known error of CityGML global registration

Readers:
- CITYGML_1: CITYGML from $(SourceDataset_CITYGML)
- PCD_1: PCD from $(SourceDataset_PCD_6)
- PCD_2: PCD from $(SourceDataset_PCD_8)

Writers:
- LAS_1: LAS to $(DestDataset_LAS)

TestFilter
    DEFAULT_VALUE = occupied
    TEST_LIST = "BOOL_OP,OR,COMPOSITE_TEST,""""""1"""""",TEST_CLAUSE,CASE_INSENSITIVE_TEST @Value(fme_basename) CONTAINS Free",free
    free -> Clipper [CLIPPEE]
    occupied -> Clipper_2 [CLIPPEE]
Decider: TestFilter
    DEFAULT_VALUE = <UNFILTERED>
    TEST_LIST:
      "BOOL_OP,OR,COMPOSITE_TEST,""""""1 OR 2"""""",TEST_CLAUSE,TEST @Value(gml_id) = $(bldSelect)
      TEST @Value(gml_parent_id) = $(bldSelect)",$(bldSelect)
    $(bldSelect) -> BoundsExtractor_2
BoundsExtractor_2
    ZMAX = maxHeight
    ZMIN = minHeight
    -> Split2parts
Split2parts: TestFilter
    DEFAULT_VALUE = <UNFILTERED>
    TEST_LIST = "BOOL_OP,OR,COMPOSITE_TEST,""""""1"""""",TEST_CLAUSE,TEST @Value(fme_feature_type) = GroundSurface",GroundSurface,"BOOL_OP,OR,COMPOSITE_TEST,""""""1"""""",TEST_CLAUSE,TEST @Value(fme_feature_type) = WallSurface",WallSurface,"BOOL_OP,OR,COMPOSITE_TEST,""""""1"""""",TEST_CLAUSE,TEST @Value(fme_feature_type) = Building",Building
    WallSurface -> 2DForcer
2DForcer
    2D -> clCityGML_2
    2D -> clCityGML
Junction_2
    -> ExpressionEvaluator_4
Junction_9
    -> ExpressionEvaluator_11

Bookmark: Octomap MLS free and occupied, test
Note: only free, with prob
PCD (reader PCD_1)
    -> Offsetter_4
Note: only occupied, with prob
PCD (reader PCD_2)
    -> Offsetter_4
Note: bring back to global coordinates, e.g., fixed offset (due to .pcd precision)
Offsetter_4
    MODE = Cartesian Coordinate
    XOFF = 690729.0567
    YOFF = 5335897.0603
    ZOFF = 500
    OFFSET -> CoordinateSystemSetter_3
Note: ETRS89
CoordinateSystemSetter_3
    COORDSYS = ETRS89.UTM-32N
    -> TestFilter

Bookmark: 1.1 CityGML TUM campus
Note: epsg 31468
Address (reader CITYGML_1)
    attributes: citygml_target_uri xml_buffer, citygml_feature_role xml_buffer, citygml_feature_role_attr_name xml_buffer, citygml_feature_role_attr_val xml_buffer, gml_description xml_buffer, gml_name xml_buffer, citygml_address xml_xml
    -> Junction
Building (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer, citygml_storey_heights_above_ground_units xml_buffer,
      citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, DatenquelleBodenhoehe xml_buffer, DatenquelleDachhoehe xml_buffer, DatenquelleLage xml_buffer, GE_LoD2_zOffset xml_buffer, Gemeindeschluessel xml_buffer, HoeheDach xml_buffer, HoeheGrund xml_buffer, Methode xml_buffer, NiedrigsteTraufeDesGebaeudes xml_buffer, Qualitaet xml_buffer, StandLK xml_buffer
    -> Junction
CityModel (reader CITYGML_1)
    attributes: citygml_target_uri xml_buffer, gml_description xml_buffer, gml_name xml_buffer, citygml_city_object_member{}.xlink_href xml_buffer, gml_feature_member{}.xlink_href xml_buffer
GroundSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, Flaeche xml_buffer, Z_MAX xml_buffer, Z_MAX_ASL xml_buffer, Z_MIN xml_buffer, Z_MIN_ASL xml_buffer
    -> Junction
RoofSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, Dachneigung xml_buffer, Dachorientierung xml_buffer, Flaeche xml_buffer, Z_MAX xml_buffer, Z_MAX_ASL xml_buffer, Z_MIN xml_buffer, Z_MIN_ASL xml_buffer
    -> Junction
WallSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, Flaeche xml_buffer, Z_MAX xml_buffer, Z_MAX_ASL xml_buffer, Z_MIN xml_buffer, Z_MIN_ASL xml_buffer
    -> Junction
Junction
    -> Reprojector
Note: to ETRS89
Reprojector
    DEST = ETRS89.UTM-32N
    INTERPOLATION_TYPE_NAME = Nearest Neighbor
    RASTER_CELL_SIZE = Preserve Cells
    RASTER_TOLERANCE = 0.0
    SOURCE = Read from feature
    REPROJECTED -> Decider

Bookmark: 2.1.1.2 CL CityGML
clCityGML: TestFilter
    DEFAULT_VALUE = <UNFILTERED>
    TEST_LIST = "BOOL_OP,OR,COMPOSITE_TEST,""""""1"""""",TEST_CLAUSE,TEST $(clCityGML) = 70",70,"BOOL_OP,OR,COMPOSITE_TEST,""""""1"""""",TEST_CLAUSE,TEST $(clCityGML) = 75",75,"BOOL_OP,OR,COMPOSITE_TEST,""""""1"""""",TEST_CLAUSE,TEST $(clCityGML) = 80",80,"BOOL_OP,OR,COMPOSITE_TEST,""""""1"""""",TEST_CLAUSE,TEST $(clCityGML) = 85",85,"BOOL_OP,OR,COMPOSITE_TEST,""""""1"""""",TEST_CLAUSE,TEST $(clCityGML) = 90",90,"BOOL_OP,OR,COMPOSITE_TEST,""""""1"""""",TEST_CLAUSE,TEST $(clCityGML) = 92",92,"BOOL_OP,OR,COMPOSITE_TEST,""""""1"""""",TEST_CLAUSE,TEST $(clCityGML) = 95",95,"BOOL_OP,OR,COMPOSITE_TEST,""""""1"""""",TEST_CLAUSE,TEST $(clCityGML) = 96",96,"BOOL_OP,OR,COMPOSITE_TEST,""""""1"""""",TEST_CLAUSE,TEST $(clCityGML) = 98",98,"BOOL_OP,OR,COMPOSITE_TEST,""""""1"""""",TEST_CLAUSE,TEST $(clCityGML) = 99",99
    70 -> AttributeCreator_12
    75 -> AttributeCreator_13
    80 -> AttributeCreator_14
    85 -> AttributeCreator_15
    90 -> AttributeCreator_16
    92 -> AttributeCreator_17
    95 -> AttributeCreator_18
    96 -> AttributeCreator_19
    98 -> AttributeCreator_20
    99 -> AttributeCreator_21
AttributeCreator_12
    ATTR_TABLE = SET_TO clZ = 1.04
    -> Junction_2
AttributeCreator_13
    ATTR_TABLE = SET_TO clZ = 1.15
    -> Junction_2
AttributeCreator_14
    ATTR_TABLE = SET_TO clZ = 1.28
    -> Junction_2
AttributeCreator_15
    ATTR_TABLE = SET_TO clZ = 1.44
    -> Junction_2
AttributeCreator_16
    ATTR_TABLE = SET_TO clZ = 1.645
    -> Junction_2
AttributeCreator_17
    ATTR_TABLE = SET_TO clZ = 1.75
    -> Junction_2
AttributeCreator_18
    ATTR_TABLE = SET_TO clZ = 1.96
    -> Junction_2
AttributeCreator_19
    ATTR_TABLE = SET_TO clZ = 2.05
    -> Junction_2
AttributeCreator_20
    ATTR_TABLE = SET_TO clZ = 2.33
    -> Junction_2
AttributeCreator_21
    ATTR_TABLE = SET_TO clZ = 2.58
    -> Junction_2

Bookmark: 2.1.1.4 calculate CityGML st dev
Note: calculate mu
ExpressionEvaluator_4
    ACTION = Create New Attribute
    EXPRESSION = @div($(eCityGML),2)
    VAL_ATTR = citygmlMu
    -> ExpressionEvaluator_5
Note: calculate st dev
ExpressionEvaluator_5
    ACTION = Create New Attribute
    EXPRESSION = @div(@Value(citygmlMu),@Value(clZ))
    VAL_ATTR = citygmlStDev
    -> FeatureMerger [REQUESTOR]

Bookmark: 2.1.1.2 CL CityGML GR
clCityGML_2: TestFilter
    DEFAULT_VALUE = <UNFILTERED>
    TEST_LIST = "BOOL_OP,OR,COMPOSITE_TEST,""""""1"""""",TEST_CLAUSE,TEST $(clGR) = 70",70,"BOOL_OP,OR,COMPOSITE_TEST,""""""1"""""",TEST_CLAUSE,TEST $(clGR) = 75",75,"BOOL_OP,OR,COMPOSITE_TEST,""""""1"""""",TEST_CLAUSE,TEST $(clGR) = 80",80,"BOOL_OP,OR,COMPOSITE_TEST,""""""1"""""",TEST_CLAUSE,TEST $(clGR) = 85",85,"BOOL_OP,OR,COMPOSITE_TEST,""""""1"""""",TEST_CLAUSE,TEST $(clGR) = 90",90,"BOOL_OP,OR,COMPOSITE_TEST,""""""1"""""",TEST_CLAUSE,TEST $(clGR) = 92",92,"BOOL_OP,OR,COMPOSITE_TEST,""""""1"""""",TEST_CLAUSE,TEST $(clGR) = 95",95,"BOOL_OP,OR,COMPOSITE_TEST,""""""1"""""",TEST_CLAUSE,TEST $(clGR) = 96",96,"BOOL_OP,OR,COMPOSITE_TEST,""""""1"""""",TEST_CLAUSE,TEST $(clGR) = 98",98,"BOOL_OP,OR,COMPOSITE_TEST,""""""1"""""",TEST_CLAUSE,TEST $(clGR) = 99",99
    70 -> AttributeCreator_6
    75 -> AttributeCreator_22
    80 -> AttributeCreator_23
    85 -> AttributeCreator_24
    90 -> AttributeCreator_25
    92 -> AttributeCreator_26
    95 -> AttributeCreator_27
    96 -> AttributeCreator_28
    98 -> AttributeCreator_29
    99 -> AttributeCreator_30
AttributeCreator_6
    ATTR_TABLE = SET_TO clZ = 1.04
    -> Junction_9
AttributeCreator_22
    ATTR_TABLE = SET_TO clZ = 1.15
    -> Junction_9
AttributeCreator_23
    ATTR_TABLE = SET_TO clZ = 1.28
    -> Junction_9
AttributeCreator_24
    ATTR_TABLE = SET_TO clZ = 1.44
    -> Junction_9
AttributeCreator_25
    ATTR_TABLE = SET_TO clZ = 1.645
    -> Junction_9
AttributeCreator_26
    ATTR_TABLE = SET_TO clZ = 1.75
    -> Junction_9
AttributeCreator_27
    ATTR_TABLE = SET_TO clZ = 1.96
    -> Junction_9
AttributeCreator_28
    ATTR_TABLE = SET_TO clZ = 2.05
    -> Junction_9
AttributeCreator_29
    ATTR_TABLE = SET_TO clZ = 2.33
    -> Junction_9
AttributeCreator_30
    ATTR_TABLE = SET_TO clZ = 2.58
    -> Junction_9

Bookmark: 2.1.1.5 calculate CityGML st dev GR
Note: calculate mu
ExpressionEvaluator_11
    ACTION = Create New Attribute
    EXPRESSION = @div($(GR),2)
    VAL_ATTR = citygmlMu
    -> ExpressionEvaluator_12
Note: calculate st dev
ExpressionEvaluator_12
    ACTION = Create New Attribute
    EXPRESSION = @div(@Value(citygmlMu),@Value(clZ))
    VAL_ATTR = citygmlGRStDev
    -> FeatureMerger [SUPPLIER]

Bookmark: Confirm / conflict
FeatureMerger
    ATTR_ACCUM_MODE = Merge Supplier
    ATTR_CONFLICT_RES = Use Requestor
    IGNORE_NULLS = No
    JOIN_KEYS = @Value(gml_id) @Value(gml_id) AUTO
    MERGE_TYPE = Attributes Only
    PROCESS_DUPS = NO
    REJECT_NULL_MISSING_KEYS = No
    SUPPLIERS_FIRST = No
    MERGED -> ExpressionEvaluator_13
Note: calculate glob. acc st dev
Note: Error for each polygon is assumed to be Gaussian-like distributed and in L1 norm. / The final conf. value is set to 95% (1.96) / mu for the final interval is equal to position of the polygon in question
ExpressionEvaluator_13
    ACTION = Create New Attribute
    EXPRESSION = @sqrt(@pow(@Value(citygmlStDev),2))
    VAL_ATTR = stDev
    -> ExpressionEvaluator_6
Note: calculate Total st dev (GR)
ExpressionEvaluator_6
    ACTION = Create New Attribute
    EXPRESSION = @sqrt(@sum(@pow(@Value(citygmlGRStDev),2),@pow(@Value(citygmlStDev),2)))
    VAL_ATTR = stDevGR
    -> ExpressionEvaluator_14
Note: calculate glob. acc. interval
ExpressionEvaluator_14
    ACTION = Create New Attribute
    EXPRESSION = @mult(@Value(stDev),2)
    VAL_ATTR = intervalCL
    -> VariableSetter_2
VariableSetter_2
    SCOPE = Global
    VALUE = @Value(intervalCL)
    VARNAME = inintCLglob
    -> Bufferer_2
Note: interval apply
Bufferer_2
    ANGLE = 22.5
    CAP_STYLE = Arc
    CORNER_STYLE = Arc
    MODE = AREA
    OFFSET = @Value(intervalCL)
    OFFSET_UNITS = NONE
    PRECISION = APPROX
    BUFFERED -> Dissolver_2
Dissolver_2
    ACCUM_INPUT_ATTRS = Use Attributes From One Feature
    CLEANING_TOLERANCE = Automatic
    CONNECT_Z_MODE = First Wins
    DEAGGREGATE_INPUT = Yes
    AREA -> Clipper [CLIPPER]
    AREA -> Clipper_2 [CLIPPER]

Bookmark: Conflict
Clipper
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> PointCloudComponentAdder_2
    OUTSIDE -> Junction_4
Note: red color
PointCloudComponentAdder_2
    COMPONENTS_TO_ADD = color_red,UInt16,255,color_green,UInt16,0,color_blue,UInt16,0
    -> conflict
    -> AttributeCreator
conflict: Inspector
AttributeCreator
    ATTR_TABLE = SET_TO name = conflict
    -> File1 (writer LAS_1)
Note: to FREE
Junction_4
    -> Junction_5

Bookmark: Free
Note: rest of Conflict set, if required
Junction_5 [off]
    -> Junction_3 [off]
Junction_3 [off]
    -> PointCloudComponentAdder_5 [off]
Note: pink color
PointCloudComponentAdder_5 [off]
    COMPONENTS_TO_ADD = color_red,UInt16,255,color_green,UInt16,105,color_blue,UInt16,180
    -> AttributeCreator_3 [off]
    -> Free [off]
Free: Inspector [off]
AttributeCreator_3 [off]
    ATTR_TABLE = SET_TO name = free
    -> File1 (writer LAS_1)

Bookmark: Confirm
Clipper_2
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> PointCloudComponentAdder
    OUTSIDE -> Junction_7
Note: green color
PointCloudComponentAdder
    COMPONENTS_TO_ADD = color_red,UInt16,0,color_green,UInt16,255,color_blue,UInt16,0
    -> confirmation
    -> AttributeCreator_2
confirmation: Inspector
AttributeCreator_2
    ATTR_TABLE = SET_TO name = confirmation
    -> File1 (writer LAS_1)
Note: to Occupied
Junction_7
    -> Junction_8

Bookmark: Occupied
Note: rest of Occupied, if required
Junction_8 [off]
    -> Junction_6 [off]
Junction_6 [off]
    -> PointCloudComponentAdder_6 [off]
Note: blue color
PointCloudComponentAdder_6 [off]
    COMPONENTS_TO_ADD = color_red,UInt16,0,color_green,UInt16,128,color_blue,UInt16,255
    -> Occupied__mls_ [off]
    -> AttributeCreator_4 [off]
Occupied__mls_: Inspector [off]
AttributeCreator_4 [off]
    ATTR_TABLE = SET_TO name = occupied
    -> File1 (writer LAS_1)

Bookmark: OUT
File1 (writer LAS_1)
