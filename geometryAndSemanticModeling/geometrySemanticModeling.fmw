FME workspace geometrySemanticModeling.fmw

Parameters:
- SourceDataset_LAS_5 = D:\projects\PassageFinder\Octomap\octomapChangeDetection\data\processed\detectedConflictsBld70\conflict.las   # Source ASPRS LAS File(s)
- SourceDataset_LAS_7 = D:\projects\PassageFinder\Octomap\octomapChangeDetection\data\processed\detectedConflictsBld70\confirmation.las   # Source ASPRS LAS File(s)
- SourceDataset_CITYGML = D:\projects\PassageFinder\data\raw\CityGML\TUM Munich\TUM Munich.gml   # Source CityGML File(s)
- SourceDataset_SHAPEFILE_4 = D:\projects\PassageFinder\data\raw\OSM\bayern-latest-free\gis_osm_roads_free_1.shp   # Source Esri Shapefile(s)
- DestDataset_CITYGML = D:\projects\PassageFinder\data\processed\octoRefinedCityGML\TUMpassage.gml   # Destination CityGML Document
- DestDataset_GEOTIFF = D:\projects\PassageFinder\BayesianOcto\facadesRasters   # Destination GeoTIFF Folder
- DestDataset_GEOTIFF_7 = D:\projects\PassageFinder\BayesianOcto\facadesRasters   # Destination GeoTIFF Folder
- DestDataset_GEOTIFF_6 = D:\projects\PassageFinder\BayesianOcto\facadesRasters   # Destination GeoTIFF Folder
- bldSelect = DEBY_LOD2_4906970   # Select building ID
- DestDataset_GEOTIFF_8 = D:\projects\PassageFinder\BayesianOcto\facadesRasters   # Destination GeoTIFF Folder
- SourceDataset_GEOTIFF = D:\projects\PassageFinder\BayesianOcto\output\underpass_Probability_underpass.tif   # Source GeoTIFF File(s)

Readers:
- LAS_2: LAS from $(SourceDataset_LAS_5)
- LAS_3: LAS from $(SourceDataset_LAS_7)
- CITYGML_1: CITYGML from $(SourceDataset_CITYGML)
- SHAPEFILE_2: SHAPEFILE from $(SourceDataset_SHAPEFILE_4) in EPSG:4326
- GEOTIFF_1: GEOTIFF from $(SourceDataset_GEOTIFF)

Writers:
- CITYGML_2: CITYGML to $(DestDataset_CITYGML)
- GEOTIFF_2: GEOTIFF to $(DestDataset_GEOTIFF)
- GEOTIFF_3: GEOTIFF to $(DestDataset_GEOTIFF_8)
- GEOTIFF_4: GEOTIFF to $(DestDataset_GEOTIFF_7)
- GEOTIFF_5: GEOTIFF to $(DestDataset_GEOTIFF_6)

Bookmark: 1.1 CityGML TUM campus
Note: epsg 31468
Address (reader CITYGML_1)
    attributes: citygml_target_uri xml_buffer, citygml_feature_role xml_buffer, citygml_feature_role_attr_name xml_buffer, citygml_feature_role_attr_val xml_buffer, gml_description xml_buffer, gml_name xml_buffer, citygml_address xml_xml
    -> Junction
Building (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer, citygml_storey_heights_above_ground_units xml_buffer,
      citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, DatenquelleBodenhoehe xml_buffer, DatenquelleDachhoehe xml_buffer, DatenquelleLage xml_buffer, GE_LoD2_zOffset xml_buffer, Gemeindeschluessel xml_buffer, HoeheDach xml_buffer, HoeheGrund xml_buffer, Methode xml_buffer, NiedrigsteTraufeDesGebaeudes xml_buffer, Qualitaet xml_buffer, StandLK xml_buffer
    -> Junction
CityModel (reader CITYGML_1)
    attributes: citygml_target_uri xml_buffer, gml_description xml_buffer, gml_name xml_buffer, citygml_city_object_member{}.xlink_href xml_buffer, gml_feature_member{}.xlink_href xml_buffer
    -> Junction_48
Note: CityModel
Junction_48
    -> Junction_49
GroundSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, Flaeche xml_buffer, Z_MAX xml_buffer, Z_MAX_ASL xml_buffer, Z_MIN xml_buffer, Z_MIN_ASL xml_buffer
    -> Junction
RoofSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, Dachneigung xml_buffer, Dachorientierung xml_buffer, Flaeche xml_buffer, Z_MAX xml_buffer, Z_MAX_ASL xml_buffer, Z_MIN xml_buffer, Z_MIN_ASL xml_buffer
    -> Junction
WallSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, Flaeche xml_buffer, Z_MAX xml_buffer, Z_MAX_ASL xml_buffer, Z_MIN xml_buffer, Z_MIN_ASL xml_buffer
    -> Junction
Junction
    -> Reprojector
Note: to ETRS89
Reprojector
    DEST = ETRS89.UTM-32N
    INTERPOLATION_TYPE_NAME = Nearest Neighbor
    RASTER_CELL_SIZE = Preserve Cells
    RASTER_TOLERANCE = 0.0
    SOURCE = Read from feature
    REPROJECTED -> Decider_3

Bookmark: CityGML
Note: CityModel
Junction_49
    -> CityModel (writer CITYGML_2)
CityModel (writer CITYGML_2)
    attributes: citygml_target_uri xml_buffer, gml_description xml_buffer, gml_name xml_buffer, citygml_city_object_member{}.xlink_href xml_buffer, citygml_appearance_member{}.xlink_href xml_buffer, gml_feature_member{}.xlink_href xml_buffer
BuildingInstallation (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_class xml_buffer, citygml_function{} xml_buffer, citygml_usage{} xml_buffer, citygml_level_of_detail{} xml_buffer, refinementDate xml_buffer, maxClearance xml_buffer
Building (writer CITYGML_2)
    attributes: citygml_feature_role xml_buffer, citygml_target_uri xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, Dachneigung xml_buffer, Dachorientierung xml_buffer, Flaeche xml_buffer, Z_MAX xml_buffer, Z_MAX_ASL xml_buffer, Z_MIN xml_buffer, Z_MIN_ASL xml_buffer, citygml_class xml_buffer, citygml_class_codeSpace xml_buffer, citygml_function{} xml_buffer, citygml_function{}.codeSpace xml_buffer, citygml_usage{} xml_buffer, citygml_usage{}.codeSpace xml_buffer, citygml_year_of_construction xml_buffer,
      citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer, citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_interior_room{}.xlink_href xml_buffer, citygml_consists_of_building_part{}.xlink_href xml_buffer, citygml_address{}.xlink_href xml_buffer, DatenquelleBodenhoehe xml_buffer, DatenquelleDachhoehe xml_buffer, DatenquelleLage xml_buffer, GE_LoD2_zOffset xml_buffer, Gemeindeschluessel xml_buffer, HoeheDach xml_buffer, HoeheGrund xml_buffer, Methode xml_buffer, NiedrigsteTraufeDesGebaeudes xml_buffer, Qualitaet xml_buffer, StandLK xml_buffer, citygml_address xml_xml, maxHeight xml_real64,
      minHeight xml_real64, refinementDate xml_buffer, volume xml_real64
CeilingSurface (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_level_of_detail{} xml_buffer, citygml_opening{}.xlink_href xml_buffer
GroundSurface (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_level_of_detail{} xml_buffer, citygml_opening{}.xlink_href xml_buffer
RoofSurface (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_level_of_detail{} xml_buffer, citygml_opening{}.xlink_href xml_buffer
WallSurface (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_level_of_detail{} xml_buffer, citygml_opening{}.xlink_href xml_buffer
BuildingPart (writer CITYGML_2)
    attributes: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
ClosureSurface (writer CITYGML_2)
    attributes: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
Door (writer CITYGML_2)
    attributes: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
Window (writer CITYGML_2)
    attributes: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

Bookmark: 2 SYSTEM
Decider_3: TestFilter
    DEFAULT_VALUE = <UNFILTERED>
    TEST_LIST:
      "BOOL_OP,OR,COMPOSITE_TEST,""""""1 OR 2"""""",TEST_CLAUSE,TEST @Value(gml_id) = $(bldSelect)
      TEST @Value(gml_parent_id) = $(bldSelect)",$(bldSelect)
    $(bldSelect) -> BoundsExtractor_2
BoundsExtractor_2
    ZMAX = maxHeight
    ZMIN = minHeight
    -> Split2parts
Split2parts: TestFilter
    DEFAULT_VALUE = <UNFILTERED>
    TEST_LIST = "BOOL_OP,OR,COMPOSITE_TEST,""""""1"""""",TEST_CLAUSE,TEST @Value(fme_feature_type) = GroundSurface",GroundSurface,"BOOL_OP,OR,COMPOSITE_TEST,""""""1"""""",TEST_CLAUSE,TEST @Value(fme_feature_type) = WallSurface",WallSurface,"BOOL_OP,OR,COMPOSITE_TEST,""""""1"""""",TEST_CLAUSE,TEST @Value(fme_feature_type) = Building",Building
    GroundSurface -> Junction_9
    WallSurface -> TestFilter_11
    Building -> Junction_17
    Building -> Junction_47
Note: to OSM
Junction_9
    -> Junction_10
Note: borders of rasterized facade
Note: to confirmation
Note: RasterPropertyExtractor : Input
Junction_8
    -> Clipper [CLIPPER]
    -> Clipper_3 [CLIPPER]
Note: Bld viz
Junction_47
    -> Junction_61
Note: vis2
Junction_61
Note: to 3D cut
Junction_17
    -> Junction_18
Note: 3D raw building geometry
Junction_18
    -> GeometryValidator_7
    -> 3dBuilding
    -> Junction_45
Note: pass atr. to saved model
Junction_45
    -> Junction_46
3dBuilding: Inspector
Note: due to the fact that citygml might have not valid raw geo!
GeometryValidator_7
    ISSUE_ATTR_NAME = _issues
    PRESETS = Surfaces And Solids
    REPAIR = Yes
    RULES = SELF_INTERSECTING CHECK_HOLE_TOUCHING_POLYGON]No]CONNECT_Z_MODE_SI]FIRST_WINS]SELF_INTERSECTION_TOLERANCE]None]FME_CONTROLLER_QUERY_FILE]transformers\dependencies\geometryvalidator\SELF_INTERSECTING.fme PLANAR_SURFACE CHECK_AREA]DO_NOT_CHECK_AREA]TOLERANCE_MODE]AUTO]TOLERANCE]0.0]ANGULAR_TOLERANCE_MODE]AUTO]ANGULAR_TOLERANCE]0.0]FME_CONTROLLER_QUERY_FILE]transformers\dependencies\geometryvalidator\PLANAR_SURFACE.fme SOLID_VOID_REPAIR  SHELL_VALIDATION FLIP_APPEARANCE_MODE]FLIP_APPEARANCES]FME_CONTROLLER_QUERY_FILE]transformers\dependencies\geometryvalidator\SHELL_VALIDATION.fme MISSING_TEXTURE_COORDINATES  SURFACE_ORIENTATION  SOLID_ORIENTATION
    SUMMARY = Detailed
    PASSED -> Junction_19
    FAILED -> Junction_19
    REPAIRED -> Junction_19
Junction_19
    -> CSGBuilder_3 [A]
Note: Aligned 3D passages spaces
Junction_16
    -> GeometryValidator_2
Note: Passage profiles with ground eraser feature and labeled parts
Junction_37
    -> CSGBuilder_3 [B]

Bookmark: Simplify to polygon
Note: Selected Building's GroundSurface
Junction_10
    -> BoundsExtractor_3
Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = Yes
    DEAGGREGATED -> GeometryCoercer
GeometryCoercer
    GQUERY:
      for $geom in //geometry
      where $geom/count(parent::geometry) = 0
      return number($geom/@fme_id)
    KIND = fme_polygon
    COERCED -> Dissolver_9

Bookmark: OSM passage detector
BoundsExtractor_3
    ZMIN = groundH
    -> Deaggregator
Dissolver_9
    ACCUM_INPUT_ATTRS = Use Attributes From One Feature
    CLEANING_TOLERANCE = Automatic
    CONNECT_Z_MODE = First Wins
    DEAGGREGATE_INPUT = Yes
    GROUP_BY = gml_parent_id
    AREA -> LineOnAreaOverlayer [AREA]

Bookmark: cut within the facade range
Note: facade of interest
TestFilter_11
    DEFAULT_VALUE = <UNFILTERED>
    TEST_LIST = "BOOL_OP,OR,COMPOSITE_TEST,""""""1"""""",TEST_CLAUSE,TEST @Value(gml_id) = DEBY_LOD2_4906970_c368b4d3-0164-4919-b93a-65c11c4df672",DEBY_LOD2_4906970_c368b4d3-0164-4919-b93a-65c11c4df672
    DEBY_LOD2_4906970_c368b4d3-0164-4919-b93a-65c11c4df672 -> Aggregator_6
Aggregator_6
    ACCUM_ATTRS_NAME = Use Attributes From One Feature
    AGGREGATE_TYPE = Homogeneous Collection (If Possible)
    ATTR_TO_TRAIT = Yes
    ID_SELECTION = ID and Parent ID
    MODE = Geometry - Assemble One Level
    PRESERVE_ID = No
    SEP = ,
    AGGREGATE -> BoundsExtractor_6
    AGGREGATE -> tmpID_5
    AGGREGATE -> 2DForcer_2
2DForcer_2
    2D -> Junction_8

Bookmark: Select lowest line of the facade and calculate orientation and XYZ position
BoundsExtractor_6
    ZMAX = maxHeight
    ZMIN = minHeight
    -> Deaggregator_3
Deaggregator_3
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = Yes
    DEAGGREGATED -> GeometryPartExtractor
GeometryPartExtractor
    GQUERY:
      for $geom in //geometry
      where $geom/@fme_geometry_type = 'IFMELine'
      return number($geom/@fme_id)
    EXTRACTED -> Chopper_2
Chopper_2
    DEAGGREGATE_INPUT = Deaggregate
    MAX_VERTICES = 2
    MODE = By Vertex
    REMNANT_ATTR = _remnant
    CHOPPED -> BoundsExtractor_5
Note: select lowest line
BoundsExtractor_5
    ZMAX = LineH
    -> TestFilter_3
TestFilter_3
    DEFAULT_VALUE = <UNFILTERED>
    TEST_LIST:
      "BOOL_OP,AND,COMPOSITE_TEST,""""""1 AND 2"""""",TEST_CLAUSE,TEST @Value(LineH) >= @sub(@Value(minHeight),0.5)
      TEST @Value(LineH) <= @sum(@Value(minHeight),0.5)",lowestLine
    lowestLine -> 2DForcer_5
2DForcer_5
    2D -> HorizontalAngleCalculator_3

Bookmark: angle and reference coordinates extract
Note: angle
HorizontalAngleCalculator_3
    ANGLE_TYPE = Feature
    UNIT_OUTPUT = DEG
    -> CoordinateExtractor
Note: first
CoordinateExtractor
    IND = 0
    MODE = Specify Coordinate
    X_ATTR = _xFirst
    Y_ATTR = _yFirst
    -> CoordinateExtractor_2
Note: last
CoordinateExtractor_2
    IND = -1
    MODE = Specify Coordinate
    X_ATTR = _xLast
    Y_ATTR = _yLast
    -> tmpID_4
    -> Junction_7
Note: tmpID_2 : Input
Junction_7
    -> Junction_24
    -> Junction_53
Note: tmpID_6 : Input
Junction_53

Bookmark: Come back to 3D position of the raw facade
Note: CoordinateExtractor_2 : Output
Junction_24
    -> tmpID_2
tmpID_2: Counter
    CNT_ATTR = _count
    DOMAIN = counter
    SCOPE = Local
    START = 0
    -> FeatureMerger [SUPPLIER]
Note: dissolve artificial extent range and aggregate profiles
SolidDissolver
    ACCUM_ATTRS_NAME = No
    SEP = ,
    Dissolved -> tmpID
tmpID: Counter
    CNT_ATTR = _count
    DOMAIN = counter
    SCOPE = Local
    START = 0
    -> FeatureMerger [REQUESTOR]
Note: somehow ImageRasterizer deltes input attributes - one need the 3D affine matrix to get back to the origin
FeatureMerger
    ATTR_ACCUM_MODE = Merge Supplier
    ATTR_CONFLICT_RES = Use Requestor
    IGNORE_NULLS = No
    JOIN_KEYS = @Value(_count) @Value(_count) AUTO
    MERGE_TYPE = Attributes Only
    PROCESS_DUPS = NO
    REJECT_NULL_MISSING_KEYS = No
    SUPPLIERS_FIRST = No
    MERGED -> CoordinateSwapper_3
CoordinateSwapper_3
    SWAP_TYPE = Y <-> Z
    -> 3DAffiner
Note: get back the correct X,Y
3DAffiner
    A = 1
    B = 0
    C = 0
    D = 0
    E = 0
    F = 1
    G = 0
    H = @Value(_yFirst)
    I = 0
    J = 0
    K = 1
    L = 0
    AFFINED -> Rotator
Note: Set orientation of the raw facade
Rotator
    ANGLE = @Value(_angle)
    XORIG = @Value(_xFirst)
    YORIG = @Value(_yFirst)
    ROTATED -> Junction_16

Bookmark: Find correct 2D projection, angle alignment
tmpID_4: Counter
    CNT_ATTR = _count
    DOMAIN = counter
    SCOPE = Local
    START = 0
    -> FeatureMerger_6 [SUPPLIER]
tmpID_5: Counter
    CNT_ATTR = _count
    DOMAIN = counter
    SCOPE = Local
    START = 0
    -> FeatureMerger_6 [REQUESTOR]
FeatureMerger_6
    ATTR_ACCUM_MODE = Merge Supplier
    ATTR_CONFLICT_RES = Use Requestor
    IGNORE_NULLS = No
    JOIN_KEYS = @Value(_count) @Value(_count) AUTO
    MERGE_TYPE = Attributes Only
    PROCESS_DUPS = NO
    REJECT_NULL_MISSING_KEYS = No
    SUPPLIERS_FIRST = No
    MERGED -> ExpressionEvaluator_3
Note: obtain correct angle
ExpressionEvaluator_3
    ACTION = Create New Attribute
    EXPRESSION = @sub(360,@Value(_angle))
    VAL_ATTR = rightAngle
    -> Rotator_2
    -> FeatureMerger_7 [SUPPLIER]
    -> FeatureMerger_8 [SUPPLIER]
    -> FeatureMerger_9 [SUPPLIER]
    -> Junction_59
    -> Junction_52
Note: to vis
Junction_52
Note: to free space
Junction_59

Bookmark: Facade rasterization
Rotator_2
    ANGLE = @Value(rightAngle)
    XORIG = @Value(_xFirst)
    YORIG = @Value(_yFirst)
    ROTATED -> CoordinateSwapper_2
Note: y to Z
CoordinateSwapper_2
    SWAP_TYPE = Y <-> Z
    -> FeatureColorSetter
Note: set raster as 0,0,0 value
FeatureColorSetter
    FILL_COLOR = 0,0,0
    MODE = Fixed
    COLORED -> ImageRasterizer
Note: Plain facade as 0 (unknown)
ImageRasterizer
    ANTI_ALIASING = No
    BACKGROUND_COLOR = 0,0,0
    FILL_WITH_NODATA = No
    INTERPRETATION_TYPE = Gray8
    ROWCOL_OR_CELLSIZE = CellSize
    SPECIFY_GROUND_EXTENTS = Use input data ground extents
    TOLERANCE = 0.5
    X_CELL_SIZE = 0.1
    Y_CELL_SIZE = 0.1
    RASTER -> Junction_25
    RASTER -> RasterCellValueReplacer_9
    RASTER -> RasterCellValueCalculator [A]
Junction_25
    -> Junction_26
Junction_28_Output: Inspector

Bookmark: Exact facade borders
Junction_26
    -> RasterPropertyExtractor
Note: extract EXACT extent of a facade
RasterPropertyExtractor
    -> tmpFacadeExtent
tmpFacadeExtent: Counter
    CNT_ATTR = tmpFacadeExtent
    DOMAIN = counter
    SCOPE = Local
    START = 0
    -> AttributeKeeper_5
AttributeKeeper_5
    CREATE_BULK_MODE_FEATURES = NO
    KEEP_ATTRS = _max_x,_max_y,_min_x,_min_y,tmpFacadeExtent
    -> Junction_22
    -> Junction_27
    -> Junction_29
    -> Junction_62
Note: to free space
Junction_62
Note: to road projection
Junction_22
    -> Junction_23
Junction_27
    -> Junction_28
Note: to conflict
Junction_29
    -> Junction_30

Bookmark: occupied space underpass
Note: facade extent
Junction_23
    -> FeatureMerger_5 [SUPPLIER]
Note: use parent ID as connector / could happen that it is not unique (for more than one facade)
Note: Add rotation at rightAngle
FeatureMerger_9
    ATTR_ACCUM_MODE = Merge Supplier
    ATTR_CONFLICT_RES = Use Requestor
    IGNORE_NULLS = No
    JOIN_KEYS = @Value(refpartid) @Value(gml_parent_id) AUTO
    MERGE_TYPE = Attributes Only
    PROCESS_DUPS = NO
    REJECT_NULL_MISSING_KEYS = No
    SUPPLIERS_FIRST = No
    MERGED -> Rotator_5
Note: rotate to right angle
Rotator_5
    ANGLE = @Value(rightAngle)
    XORIG = @Value(_xFirst)
    YORIG = @Value(_yFirst)
    ROTATED -> CoordinateSwapper_6
Note: y to Z
CoordinateSwapper_6
    SWAP_TYPE = Y <-> Z
    -> 2DForcer_3
2DForcer_3
    2D -> Deaggregator_2
Deaggregator_2
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = Yes
    DEAGGREGATED -> GeometryFilter
Note: filter out some trash like multi lines
GeometryFilter
    BREAK_AGG = No
    GEOM_PORT_NAMES = Area Surface
    AREA -> Dissolver
    SURFACE -> Dissolver
Dissolver
    ACCUM_INPUT_ATTRS = Use Attributes From One Feature
    CLEANING_TOLERANCE = Automatic
    CONNECT_Z_MODE = First Wins
    DEAGGREGATE_INPUT = Yes
    AREA -> tmpFacadeExtent_4
tmpFacadeExtent_4: Counter
    CNT_ATTR = tmpFacadeExtent
    DOMAIN = counter
    SCOPE = Local
    START = 0
    -> FeatureMerger_5 [REQUESTOR]
FeatureMerger_5
    ATTR_ACCUM_MODE = Merge Supplier
    ATTR_CONFLICT_RES = Use Requestor
    IGNORE_NULLS = No
    JOIN_KEYS = @Value(tmpFacadeExtent) @Value(tmpFacadeExtent) AUTO
    MERGE_TYPE = Attributes Only
    PROCESS_DUPS = NO
    REJECT_NULL_MISSING_KEYS = No
    SUPPLIERS_FIRST = No
    MERGED -> FeatureColorSetter_2
Note: set raster as 1,1,1 value
FeatureColorSetter_2
    FILL_COLOR = 1,1,1
    MODE = Fixed
    COLORED -> ImageRasterizer_5
Note: rasterize and make zero-background
ImageRasterizer_5
    ANTI_ALIASING = No
    BACKGROUND_COLOR = 0,0,0
    FILL_WITH_NODATA = No
    GROUND_EXTENTS_MAX_X = @Value(_max_x)
    GROUND_EXTENTS_MAX_Y = @Value(_max_y)
    GROUND_EXTENTS_MIN_X = @Value(_min_x)
    GROUND_EXTENTS_MIN_Y = @Value(_min_y)
    INTERPRETATION_TYPE = Gray8
    ROWCOL_OR_CELLSIZE = CellSize
    SPECIFY_GROUND_EXTENTS = Specify ground extents
    TOLERANCE = 0.5
    X_CELL_SIZE = 0.1
    Y_CELL_SIZE = 0.1
    RASTER -> RasterCellValueReplacer_7
Note: Underpass range as value 4
RasterCellValueReplacer_7
    NEW_VALUE = 4
    REPLACE_GREATER_THAN = 254
    REPLACE_NODATA = No
    -> RasterCellValueReplacer_5

Bookmark: Map Confirmation
Note: add correct facade extent
Junction_28
    -> FeatureMerger_3 [SUPPLIER]
    -> Junction_28_Output
Note: LAS
Junction_5
    -> Clipper [CLIPPEE]
Clipper
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> FeatureMerger_7 [REQUESTOR]
Note: use gmlID as connector
Note: Add rotation at rightAngle
FeatureMerger_7
    ATTR_ACCUM_MODE = Merge Supplier
    ATTR_CONFLICT_RES = Use Requestor
    IGNORE_NULLS = No
    JOIN_KEYS = @Value(gml_id) @Value(gml_id) AUTO
    MERGE_TYPE = Attributes Only
    PROCESS_DUPS = NO
    REJECT_NULL_MISSING_KEYS = No
    SUPPLIERS_FIRST = No
    MERGED -> Rotator_3
Note: rotate to right angle
Rotator_3
    ANGLE = @Value(rightAngle)
    XORIG = @Value(_xFirst)
    YORIG = @Value(_yFirst)
    ROTATED -> CoordinateSwapper
Note: y to Z
CoordinateSwapper
    SWAP_TYPE = Y <-> Z
    -> tmpFacadeExtent_2
tmpFacadeExtent_2: Counter
    CNT_ATTR = tmpFacadeExtent
    DOMAIN = counter
    SCOPE = Local
    START = 0
    -> FeatureMerger_3 [REQUESTOR]
    -> tmpFacadeExtent_2_Output
FeatureMerger_3
    ATTR_ACCUM_MODE = Merge Supplier
    ATTR_CONFLICT_RES = Use Requestor
    IGNORE_NULLS = No
    JOIN_KEYS = @Value(tmpFacadeExtent) @Value(tmpFacadeExtent) AUTO
    MERGE_TYPE = Attributes Only
    PROCESS_DUPS = NO
    REJECT_NULL_MISSING_KEYS = No
    SUPPLIERS_FIRST = No
    MERGED -> ImageRasterizer_2
ImageRasterizer_2
    ANTI_ALIASING = No
    BACKGROUND_COLOR = 1,1,1
    FILL_WITH_NODATA = No
    GROUND_EXTENTS_MAX_X = @Value(_max_x)
    GROUND_EXTENTS_MAX_Y = @Value(_max_y)
    GROUND_EXTENTS_MIN_X = @Value(_min_x)
    GROUND_EXTENTS_MIN_Y = @Value(_min_y)
    INTERPRETATION_TYPE = Gray8
    ROWCOL_OR_CELLSIZE = CellSize
    SPECIFY_GROUND_EXTENTS = Specify ground extents
    TOLERANCE = 0.5
    X_CELL_SIZE = 0.1
    Y_CELL_SIZE = 0.1
    RASTER -> RasterCellValueReplacer
Note: Confirmation as value 1
RasterCellValueReplacer
    NEW_VALUE = 1
    REPLACE_LESS_THAN = 254
    REPLACE_NODATA = No
    -> RasterCellValueReplacer_3
Note: Other as value 0
RasterCellValueReplacer_3
    NEW_VALUE = 0
    REPLACE_GREATER_THAN = 255
    REPLACE_NODATA = No
    -> RasterCellValueReplacer_8
    -> RasterCellValueCalculator [B]
tmpFacadeExtent_2_Output: Inspector

Bookmark: Map Conflict
Note: add correct facade extent
Junction_30
    -> FeatureMerger_4 [SUPPLIER]
Note: LAS
Junction_3
    -> Clipper_3 [CLIPPEE]
Clipper_3
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> FeatureMerger_8 [REQUESTOR]
Note: use gmlID as connector
Note: Add rotation at rightAngle
FeatureMerger_8
    ATTR_ACCUM_MODE = Merge Supplier
    ATTR_CONFLICT_RES = Use Requestor
    IGNORE_NULLS = No
    JOIN_KEYS = @Value(gml_id) @Value(gml_id) AUTO
    MERGE_TYPE = Attributes Only
    PROCESS_DUPS = NO
    REJECT_NULL_MISSING_KEYS = No
    SUPPLIERS_FIRST = No
    MERGED -> Rotator_4
Note: rotate to right angle
Rotator_4
    ANGLE = @Value(rightAngle)
    XORIG = @Value(_xFirst)
    YORIG = @Value(_yFirst)
    ROTATED -> CoordinateSwapper_4
Note: y to Z
CoordinateSwapper_4
    SWAP_TYPE = Y <-> Z
    -> tmpFacadeExtent_3
tmpFacadeExtent_3: Counter
    CNT_ATTR = tmpFacadeExtent
    DOMAIN = counter
    SCOPE = Local
    START = 0
    -> FeatureMerger_4 [REQUESTOR]
FeatureMerger_4
    ATTR_ACCUM_MODE = Merge Supplier
    ATTR_CONFLICT_RES = Use Requestor
    IGNORE_NULLS = No
    JOIN_KEYS = @Value(tmpFacadeExtent) @Value(tmpFacadeExtent) AUTO
    MERGE_TYPE = Attributes Only
    PROCESS_DUPS = NO
    REJECT_NULL_MISSING_KEYS = No
    SUPPLIERS_FIRST = No
    MERGED -> ImageRasterizer_3
ImageRasterizer_3
    ANTI_ALIASING = No
    BACKGROUND_COLOR = 1,1,1
    FILL_WITH_NODATA = No
    GROUND_EXTENTS_MAX_X = @Value(_max_x)
    GROUND_EXTENTS_MAX_Y = @Value(_max_y)
    GROUND_EXTENTS_MIN_X = @Value(_min_x)
    GROUND_EXTENTS_MIN_Y = @Value(_min_y)
    INTERPRETATION_TYPE = Gray8
    ROWCOL_OR_CELLSIZE = CellSize
    SPECIFY_GROUND_EXTENTS = Specify ground extents
    TOLERANCE = 0.5
    X_CELL_SIZE = 0.1
    Y_CELL_SIZE = 0.1
    RASTER -> RasterCellValueReplacer_2
Note: Conflict as value 2
RasterCellValueReplacer_2
    NEW_VALUE = 2
    REPLACE_LESS_THAN = 254
    REPLACE_NODATA = No
    -> RasterCellValueReplacer_4
Note: Other as value 0
RasterCellValueReplacer_4
    NEW_VALUE = 0
    REPLACE_GREATER_THAN = 255
    REPLACE_NODATA = No
    -> RasterCellValueReplacer_6
    -> RasterCellValueCalculator_2 [B]

Bookmark: to the BayNet
Note: unknown range as value 255
RasterCellValueReplacer_9
    NEW_VALUE = 255
    REPLACE_GREATER_THAN = 0
    REPLACE_LESS_THAN = 0
    REPLACE_NODATA = No
    -> RasterCellValueReplacer_10
Note: the rest as 0
RasterCellValueReplacer_10
    NEW_VALUE = 0
    REPLACE_GREATER_THAN = 1
    REPLACE_LESS_THAN = 254
    REPLACE_NODATA = No
    -> unknown (writer GEOTIFF_3)
unknown (writer GEOTIFF_3)
Note: conflict range as value 255
RasterCellValueReplacer_6
    NEW_VALUE = 255
    REPLACE_GREATER_THAN = 2
    REPLACE_NODATA = No
    -> conflict (writer GEOTIFF_5)
conflict (writer GEOTIFF_5)
Note: confirm range as value 255
RasterCellValueReplacer_8
    NEW_VALUE = 255
    REPLACE_GREATER_THAN = 1
    REPLACE_NODATA = No
    -> confirm (writer GEOTIFF_4)
confirm (writer GEOTIFF_4)
Note: Underpass range as value 255
RasterCellValueReplacer_5
    NEW_VALUE = 255
    REPLACE_GREATER_THAN = 4
    REPLACE_NODATA = No
    -> road (writer GEOTIFF_2)
road (writer GEOTIFF_2)

Bookmark: Building only
Note: RAW building attributes
Junction_46
    -> FeatureMerger_10 [SUPPLIER]
Note: expose id of a building
AttributeExposer_3
    ATTR_LIST = gml_id
    -> AttributeKeeper_7
Note: only id
AttributeKeeper_7
    CREATE_BULK_MODE_FEATURES = NO
    KEEP_ATTRS = gml_id
    -> FeatureMerger_10 [REQUESTOR]
Note: Only attributes / set raw attirbutes back to building
FeatureMerger_10
    ATTR_ACCUM_MODE = Merge Supplier
    ATTR_CONFLICT_RES = Use Requestor
    IGNORE_NULLS = No
    JOIN_KEYS = @Value(gml_id) @Value(gml_id) AUTO
    MERGE_TYPE = Attributes Only
    PROCESS_DUPS = NO
    REJECT_NULL_MISSING_KEYS = No
    SUPPLIERS_FIRST = No
    MERGED -> DateTimeStamper

Bookmark: LAS
Note: conflict
LAS (reader LAS_2)
    -> Junction_2
Note: conflict
Junction_2
    -> Junction_3
Note: confirmation
LAS (reader LAS_3)
    -> Junction_4
Note: confirmation
Junction_4
    -> Junction_5

Bookmark: rc ratio
Note: 1. add plain facade to confirmation
RasterCellValueCalculator
    ACCUMULATE_ATTRIBUTES = Yes
    OPERATION = +
    PRESERVE_INTERPRETATION = Yes
    -> RasterCellValueCalculator_2 [A]
Note: 2. Add plain facade + confirmation + conflict
RasterCellValueCalculator_2
    ACCUMULATE_ATTRIBUTES = Yes
    OPERATION = +
    PRESERVE_INTERPRETATION = Yes
    -> RasterToPolygonCoercer_4
Note: create blobs
RasterToPolygonCoercer_4
    EXTRACT_NODATA = No
    LABEL_ATTRIBUTE = _label
    PRESERVE_ATTRIBUTES = Yes
    POLYGONS -> AreaCalculator_3
AreaCalculator_3
    AREA_ATTR = _area
    AREA_TYPE = Plane Area
    MULT = 1
    -> StatisticsCalculator
    -> Tester
Note: caclulate full face area
StatisticsCalculator
    CALCULATION_MODE = NUMERIC
    FEAT_STATS = _area,NUMERIC_MODE,,,,SUM,,,,,,,,
    SUMMARY -> tmpIDa
tmpIDa: AttributeCreator
    ATTR_TABLE = SET_TO tmpID = 1
    -> FeatureMerger_11 [REQUESTOR]
Tester
    BOOL_OP = OR
    COMPOSITE_TEST = 1
    TEST_CLAUSE = TEST @Value(_label) = 2
    TEST_MODE = TEST
    PASSED -> StatisticsCalculator_2
Note: caclulate full conflict area
StatisticsCalculator_2
    CALCULATION_MODE = NUMERIC
    FEAT_STATS = _area,NUMERIC_MODE,,,,SUM,,,,,,,,
    SUMMARY -> tmpIDa_2
tmpIDa_2: AttributeCreator
    ATTR_TABLE = SET_TO tmpID = 1
    -> FeatureMerger_11 [SUPPLIER]
FeatureMerger_11
    ATTR_ACCUM_MODE = Prefix Supplier
    IGNORE_NULLS = No
    JOIN_KEYS = @Value(tmpID) @Value(tmpID) AUTO
    MERGE_TYPE = Attributes Only
    PROCESS_DUPS = NO
    REJECT_NULL_MISSING_KEYS = No
    SUPPLIERS_FIRST = No
    SUPPLIER_PREFIX = _sup
    MERGED -> ExpressionEvaluator_5
ExpressionEvaluator_5
    ACTION = Create New Attribute
    EXPRESSION = (@div(@Value(_sup_area.sum),@Value(_area.sum))*100)/100
    VAL_ATTR = rc
    -> Tester_2
Note: rc threshold
Tester_2
    BOOL_OP = OR
    COMPOSITE_TEST = 1
    TEST_CLAUSE = NUM_TEST @Value(rc) RANGE [0.1,0.6]
    TEST_MODE = TEST
    FAILED -> Terminator

Bookmark: Detection and grouping of conflicts
Note: Pause to process the images in R Studio - run Bayesian Network
Note: Read results of the Bayesian Network
Terminator
    MESSAGE = Translation Terminated due to exceeding rc ratio

Bookmark: 1.2 OSM roads - lines
gis_osm_roads_free_1 (reader SHAPEFILE_2)
    attributes: osm_id char(10), code short, fclass char(28), name char(100), ref char(20), oneway char(1), maxspeed short, layer number(12,0), bridge char(1), tunnel char(1)
    -> Reprojector_2
Note: TO epsg 25832
Reprojector_2
    DEST = ETRS89.UTM-32N
    INTERPOLATION_TYPE_NAME = Nearest Neighbor
    RASTER_CELL_SIZE = Preserve Cells
    RASTER_TOLERANCE = 0.0
    SOURCE = Read from feature
    REPROJECTED -> TestFilter_2

Bookmark: Select only drivable roads
TestFilter_2
    DEFAULT_VALUE = AllGood
    TEST_LIST = "BOOL_OP,OR,COMPOSITE_TEST,""""""1"""""",TEST_CLAUSE,TEST @Value(fclass) = footway",footway,"BOOL_OP,OR,COMPOSITE_TEST,""""""1"""""",TEST_CLAUSE,TEST @Value(fclass) = pedestrian",pedestrian,"BOOL_OP,OR,COMPOSITE_TEST,""""""1"""""",TEST_CLAUSE,TEST @Value(fclass) = bridleway",bridleway,"BOOL_OP,OR,COMPOSITE_TEST,""""""1"""""",TEST_CLAUSE,TEST @Value(fclass) = cycleway",cycleway,"BOOL_OP,OR,COMPOSITE_TEST,""""""1"""""",TEST_CLAUSE,TEST @Value(fclass) = Path",Path,"BOOL_OP,OR,COMPOSITE_TEST,""""""1"""""",TEST_CLAUSE,TEST @Value(fclass) = steps",steps,"BOOL_OP,OR,COMPOSITE_TEST,""""""1"""""",TEST_CLAUSE,TEST @Value(fclass) = unknown",unknown
    AllGood -> LineOnAreaOverlayer [LINE]

Bookmark: Buildings Intersecting with Roads
LineOnAreaOverlayer
    CANDIDATE_LIST_ATTRS_TO_INCLUDE = osm_id
    CANDIDATE_LIST_ATTRS_TO_INCLUDE_MODE = Selected Attributes
    CANDIDATE_LIST_NAME = road_ids
    CLEANING_TOLERANCE = Automatic
    DEAGGREGATE_INPUT = Yes
    LIST_ATTRS_TO_INCLUDE = gml_id gml_parent_id groundH
    LIST_NAME = bld_ids
    OV_ATTR = _overlaps
    LINE -> RoadUnderPass_2
    AREA -> BldOverpasses_2

Bookmark: building
BldOverpasses_2: Tester
    BOOL_OP = OR
    COMPOSITE_TEST = 1
    TEST_CLAUSE = TEST @Value(_overlaps) >= 1
    TEST_MODE = TEST
    PASSED -> PassYes2
PassYes2: AttributeCreator
    ATTR_TABLE = SET_TO passage = 1
    -> AttributeKeeper
Note: keep related road id
AttributeKeeper
    CREATE_BULK_MODE_FEATURES = NO
    KEEP_ATTRS = gml_id,gml_parent_id,passage
    KEEP_LIST = road_ids{}.osm_id

Bookmark: SetOnlyPassages
RoadUnderPass_2: Tester
    BOOL_OP = OR
    COMPOSITE_TEST = 1
    TEST_CLAUSE = TEST @Value(_overlaps) >= 1
    TEST_MODE = TEST
    PASSED -> PassYes
PassYes: AttributeCreator
    ATTR_TABLE = SET_TO passage = 1
    -> ListExploder
ListExploder
    ATTR_ACCUM_MODE = Merge List Attributes
    ATTR_CONFLICT_RES = Use List Attribute Values
    INDEX_ATTR = _element_index
    LIST_ATTR = bld_ids{}
    ELEMENTS -> AttributeRemover
AttributeRemover
    REMOVE_ATTRS = _overlaps,_element_index
    -> AttributeRenamer
AttributeRenamer
    ATTR_TABLE:
      RENAME_SET_DEFAULT gml_id > refgmlid
      RENAME_SET_DEFAULT gml_parent_id > refpartid
    -> LineCombiner

Bookmark: Buffer roads and extrude to height
LineCombiner
    ACCUM_ATTRS_NAME = Use Attributes From One Feature
    BREAK = no
    CONNECT_Z_MODE = First Wins
    CONSIDER_NODE_ELEVATION = no
    DEAGGREGATE_GEOMETRY = Deaggregate
    DIRECTION_NAME = direction
    JUNCTIONS_IGNORE_ATTRIBUTES = No
    LINES_AS_SEGMENTS = No
    PRESERVE = no
    TOPOLOGY = End noded
    LINE -> LengthCalculator
Note: later -> for extrusion of the underpass profiles
LengthCalculator
    DIM = 2
    LEN_ATTR = _length
    MULT = 1
    -> ExpressionEvaluator
    -> Junction_14
Note: supply later with the length of extrusion
Junction_14
    -> Junction_15

Bookmark: Confidence value - upper bound
Note: for CL = 75%, z=1.15 / mu = 5.83 based on Mordechai studies
Note: st. dev.1 = mu / z score for certain CL
ExpressionEvaluator
    ACTION = Create New Attribute
    EXPRESSION = @div(5.83,1.15)
    VAL_ATTR = std1
    -> ExpressionEvaluator_2
Note: add the buffer coming from width of a road
Note: 1.5m for service road
Note: it is only one std, thus we can skip the sqr part
ExpressionEvaluator_2
    ACTION = Create New Attribute
    EXPRESSION = @sum(@Value(std1),4.5)
    VAL_ATTR = bufferValue
    -> Bufferer_4
Note: 2d buffer
Bufferer_4
    ANGLE = 22.5
    CAP_STYLE = Arc
    CORNER_STYLE = Arc
    MODE = AREA
    OFFSET = @Value(bufferValue)
    OFFSET_UNITS = NONE
    PRECISION = APPROX
    BUFFERED -> 3DForcer

Bookmark: 3d buffer
3DForcer
    KEEPZVAL = No
    ZVALATTR = @Value(groundH)
    -> Extruder
Note: based on Beil = 4.5m
Note: based on all in the Internet - 6.5m
Extruder
    DIRECTION = Vertical
    DISTANCE = 6.5
    EXTRUDED -> FeatureMerger_9 [REQUESTOR]

Bookmark: Underpass profiles, clearance spaces in 3D
Note: length of tthe road with underpass
Junction_15
    -> AttributeKeeper_3
AttributeKeeper_3
    CREATE_BULK_MODE_FEATURES = NO
    KEEP_ATTRS = _length
    -> tmpIDlength_2
tmpIDlength_2: AttributeCreator
    ATTR_TABLE = SET_TO tmpIDlength = 1
    -> FeatureMerger_2 [SUPPLIER]
tmpIDlength: AttributeCreator
    ATTR_TABLE = SET_TO tmpIDlength = 1
    -> FeatureMerger_2 [REQUESTOR]
FeatureMerger_2
    ATTR_ACCUM_MODE = Merge Supplier
    ATTR_CONFLICT_RES = Use Requestor
    IGNORE_NULLS = No
    JOIN_KEYS = @Value(tmpIDlength) @Value(tmpIDlength) AUTO
    MERGE_TYPE = Attributes Only
    PROCESS_DUPS = NO
    REJECT_NULL_MISSING_KEYS = No
    SUPPLIERS_FIRST = No
    MERGED -> AttributeKeeper_4
Note: cleaning
AttributeKeeper_4
    CREATE_BULK_MODE_FEATURES = NO
    KEEP_ATTRS = _length
    -> tmpProfileID
tmpProfileID: Counter
    CNT_ATTR = tmpProfileID
    DOMAIN = counter
    SCOPE = Local
    START = 0
    -> Extruder_2
    -> Extruder_3
Note: length + 0.2m extent to cut seamlessly the later building
Note: extrude profiles to the extents of building
Extruder_2
    DIRECTION = Vertical
    DISTANCE = @sum(@Value(_length),0.2)
    EXTRUDED -> SolidDissolver [Solids]
Note: extrude profiles to the extents of building
Note: - 0.2m extent to cut seamlessly the later building
Extruder_3
    DIRECTION = Vertical
    DISTANCE = -0.2
    EXTRUDED -> SolidDissolver [Solids]

Bookmark: determination of underpass groups
Note: read results of the R script
GEOTIFF (reader GEOTIFF_1)
    -> RasterToPolygonCoercer_2
Note: create blobs
RasterToPolygonCoercer_2
    EXTRACT_NODATA = No
    LABEL_ATTRIBUTE = probability
    PRESERVE_ATTRIBUTES = Yes
    POLYGONS -> AreaCalculator_2
AreaCalculator_2
    AREA_ATTR = _area
    AREA_TYPE = Plane Area
    MULT = 1
    -> Tester_3
Note: select only underpass blobs, P threshold (Phigh)
Tester_3
    BOOL_OP = OR
    COMPOSITE_TEST = 1
    TEST_CLAUSE = TEST @Value(probability) > 0.7
    TEST_MODE = TEST
    PASSED -> AreaCalculator

Bookmark: filter out small segments
AreaCalculator
    AREA_ATTR = _area
    AREA_TYPE = Plane Area
    MULT = 1
    -> Tester_6
Tester_6
    BOOL_OP = OR
    COMPOSITE_TEST = 1
    TEST_CLAUSE = TEST @Value(_area) > 1.5
    TEST_MODE = TEST
    PASSED -> Junction_11
Note: >1.5m, / bs parameter
Junction_11
    -> DonutHoleExtractor_3

Bookmark: Generalize only with Douglas
Note: in case of donuts -> dissolve them
DonutHoleExtractor_3
    DEAGGREGATE_INPUT = Yes
    OUTERSHELL -> Generalizer_4
Note: Douglas-P to simplify
Generalizer_4
    ALG_TEXT = Douglas (Generalize)
    CLEANING_TOLERANCE = Automatic
    PRESERVE = Yes
    PRESERVE_PATHS = No
    TOLERANCE = 0.1
    -> DonutHoleExtractor
Note: in case of donuts -> dissolve them
DonutHoleExtractor
    DEAGGREGATE_INPUT = Yes
    OUTERSHELL -> SpikeRemover
Note: erase possible spikes -- <45deg
SpikeRemover
    DIMENSIONS = 2D
    ITERATIVE = Yes
    SPIKEANGLE = 45
    UNCHANGED -> Junction_31
    CHANGED -> Junction_31
Junction_31
    -> Generalizer_5
Note: Douglas-P to simplify, after spikes removal
Generalizer_5
    ALG_TEXT = Douglas (Generalize)
    CLEANING_TOLERANCE = Automatic
    PRESERVE = Yes
    PRESERVE_PATHS = No
    TOLERANCE = 0.3
    -> GeometryValidator_4
Note: assure left orientation of polygon
GeometryValidator_4
    ISSUE_ATTR_NAME = _issues
    PRESETS = Custom
    REPAIR = Yes
    RULES = AREA_ORIENTATION AREA_ORIENTATION]LEFT]FME_CONTROLLER_QUERY_FILE]transformers/dependencies/geometryvalidator/AREA_ORIENTATION.fme
    SUMMARY = Detailed
    PASSED -> AttributeRemover_3
    FAILED -> AttributeRemover_3
    REPAIRED -> AttributeRemover_3
Note: erase tmp IDs
AttributeRemover_3
    LIST_ATTRS = _issues{} _issues{}.count _issues{}.issue_found _issues{}.location_sample.x _issues{}.location_sample.y _issues{}.location_sample.z _issues{}.repair_state
    REMOVE_ATTRS = groupingTmp,tmpIDhull
    -> tmpIDline
tmpIDline: Counter
    CNT_ATTR = tmpIDline
    DOMAIN = counter
    SCOPE = Local
    START = 0
    -> BoundsExtractor_8
    -> Dissolver_6

Bookmark: lowest line selection
BoundsExtractor_8
    YMIN = minLineH
    -> GeometryPartExtractor_6
GeometryPartExtractor_6
    GQUERY:
      for $geom in //geometry
      where $geom/@fme_geometry_type = 'IFMELine'
      return number($geom/@fme_id)
    EXTRACTED -> Chopper_3
Chopper_3
    DEAGGREGATE_INPUT = Deaggregate
    MAX_VERTICES = 2
    MODE = By Vertex
    REMNANT_ATTR = _remnant
    CHOPPED -> BoundsExtractor_7
Note: select lowest line
BoundsExtractor_7
    YMAX = LineH
    -> TestFilter_7
    -> BoundsExtractor_7_Output
BoundsExtractor_7_Output: Inspector
Note: +-0.5
TestFilter_7
    DEFAULT_VALUE = <UNFILTERED>
    TEST_LIST:
      "BOOL_OP,AND,COMPOSITE_TEST,""""""1 AND 2"""""",TEST_CLAUSE,TEST @Value(LineH) >= @sub(@Value(minLineH),0.5)
      TEST @Value(LineH) <= @sum(@Value(minLineH),0.5)",lowestLine
    lowestLine -> BoundingBoxReplacer
    lowestLine -> TestFilter_7_lowestLine
    <UNFILTERED> -> TestFilter_7__Unfiltered_
TestFilter_7_lowestLine: Inspector
TestFilter_7__Unfiltered_: Inspector
BoundingBoxReplacer
    BOXTYPE = 2D Bounding Box
    BOX -> GeometryFilter_2
GeometryFilter_2
    BREAK_AGG = No
    GEOM_PORT_NAMES = Line Area
    LINE -> Junction_40
    AREA -> Junction_41
    AREA -> GeometryValidator
Note: tilits levaraging areas
Junction_41
    -> Dissolver_5
Note: assure left orientation of polygon
GeometryValidator
    ISSUE_ATTR_NAME = _issues
    PRESETS = Custom
    REPAIR = Yes
    RULES = AREA_ORIENTATION AREA_ORIENTATION]LEFT]FME_CONTROLLER_QUERY_FILE]transformers/dependencies/geometryvalidator/AREA_ORIENTATION.fme
    SUMMARY = Detailed
    PASSED -> Junction_38
    FAILED -> Junction_38
    REPAIRED -> Junction_38
Junction_38
    -> AttributeKeeper_2
Note: erase attributes to perform the same operation for BBoxes
AttributeKeeper_2
    CREATE_BULK_MODE_FEATURES = NO
    KEEP_ATTRS = tmpIDline
    -> BoundsExtractor_10
BoundsExtractor_10
    YMIN = minLineH
    -> GeometryPartExtractor_7
GeometryPartExtractor_7
    GQUERY:
      for $geom in //geometry
      where $geom/@fme_geometry_type = 'IFMELine'
      return number($geom/@fme_id)
    EXTRACTED -> Chopper_4
Chopper_4
    DEAGGREGATE_INPUT = Deaggregate
    MAX_VERTICES = 2
    MODE = By Vertex
    REMNANT_ATTR = _remnant
    CHOPPED -> BoundsExtractor_9
Note: select lowest line
BoundsExtractor_9
    YMAX = LineH
    -> TestFilter_8
TestFilter_8
    DEFAULT_VALUE = <UNFILTERED>
    TEST_LIST:
      "BOOL_OP,AND,COMPOSITE_TEST,""""""1 AND 2"""""",TEST_CLAUSE,TEST @Value(LineH) >= @sub(@Value(minLineH),0.05)
      TEST @Value(LineH) <= @sum(@Value(minLineH),0.05)",lowestLine
    lowestLine -> LineExtender
    lowestLine -> LineCombiner_2
LineExtender
    LEN = 0
    END -> LineCombiner_2
LineCombiner_2
    ACCUM_ATTRS_NAME = Use Attributes From One Feature
    BREAK = no
    CONNECT_Z_MODE = First Wins
    CONSIDER_NODE_ELEVATION = no
    DEAGGREGATE_GEOMETRY = Deaggregate
    DIRECTION_NAME = direction
    JUNCTIONS_IGNORE_ATTRIBUTES = No
    LINES_AS_SEGMENTS = No
    PRESERVE = no
    TOPOLOGY = End noded
    LINE -> Junction_40
Note: lowest lines
Junction_40
    -> OffsetCurveGenerator [LINES]
    -> Aggregator_2

Bookmark: Generate areal offset
Note: 2m
OffsetCurveGenerator
    CORNER_STYLE = Bevel
    OFFSET = 2
    RIGHT -> Aggregator_2
Aggregator_2
    ACCUM_ATTRS_NAME = Use Attributes From One Feature
    AGGREGATE_TYPE = Homogeneous Collection (If Possible)
    GROUP_BY = tmpIDline
    MODE = Geometry - Assemble One Level
    SEP = ,
    AGGREGATE -> BoundingBoxReplacer_2
BoundingBoxReplacer_2
    BOXTYPE = 2D Bounding Box
    BOX -> Dissolver_5

Bookmark: Generate extended profiles to erase ground features (so-called border effect)
Note: dissolve generated offsets
Dissolver_5
    ACCUM_INPUT_ATTRS = Use Attributes From One Feature
    CLEANING_TOLERANCE = Automatic
    CONNECT_Z_MODE = First Wins
    DEAGGREGATE_INPUT = Yes
    GROUP_BY = tmpIDline
    AREA -> Dissolver_6

Bookmark: Dissolve ground offset with profiles
Note: dissolve generated offsets with profiles
Dissolver_6
    ACCUM_INPUT_ATTRS = Use Attributes From One Feature
    CLEANING_TOLERANCE = Automatic
    CONNECT_Z_MODE = First Wins
    DEAGGREGATE_INPUT = Yes
    GROUP_BY = tmpIDline
    AREA -> GeometryValidator_6
Note: check for errors, right-hand rule
GeometryValidator_6
    ISSUE_ATTR_NAME = _issues
    PRESETS = Custom
    REPAIR = Yes
    RULES = AREA_ORIENTATION AREA_ORIENTATION]RIGHT]FME_CONTROLLER_QUERY_FILE]transformers/dependencies/geometryvalidator/AREA_ORIENTATION.fme CONSECUTIVE_IDENTICAL_VERTICES_2D CHECK_Z]NO]TOLERANCE]0.0]FME_CONTROLLER_QUERY_FILE]transformers/dependencies/geometryvalidator/CONSECUTIVE_IDENTICAL_VERTICES_2D.fme OGC_VALID_CHECK OGC_VERSION]V1.2.0]FME_CONTROLLER_QUERY_FILE]transformers/dependencies/geometryvalidator/OGC_VALID_CHECK.fme OGC_SIMPLE_CHECK  SELF_INTERSECTING CHECK_HOLE_TOUCHING_POLYGON]No]CONNECT_Z_MODE_SI]FIRST_WINS]SELF_INTERSECTION_TOLERANCE]Automatic]FME_CONTROLLER_QUERY_FILE]transformers/dependencies/geometryvalidator/SELF_INTERSECTING.fme TYPE_REPAIR CONNECT_Z_MODE]FIRST_WINS]ARC_ENDPOINT_TOLERANCE_MODE]Auto]ARC_ENDPOINT_TOLERANCE]<Unused>]FME_CONTROLLER_QUERY_FILE]transformers/dependencies/geometryvalidator/TYPE_REPAIR.fme
    SUMMARY = Detailed
    PASSED -> Junction_34
    FAILED -> Junction_34
    REPAIRED -> Junction_34
Junction_34
    -> DonutHoleExtractor_2
Note: in case of donuts -> dissolve them
DonutHoleExtractor_2
    DEAGGREGATE_INPUT = Yes
    OUTERSHELL -> Junction_13
Note: underpass profile(s)
Junction_13
    -> tmpIDlength

Bookmark: Clearance space - Calculate normals and mark as walls, roofs and ground
Note: Create surface normals
GeometryValidator_2
    MISSING_VERTEX_NORMALS = MISSING_VERTEX_NORMALS
    PRESETS = Custom
    REPAIR = Yes
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%SHELL_VALIDATION_PARAMS%"Yes"%SOLID_VOID_REPAIR%""%"Yes"%OGC_SIMPLE_CHECK%""%"No"%OGC_VALID_CHECK%OGC_VALID_PARAMS%"No"%MISSING_TEXTURE_COORDINATES%""%"Yes"%MISSING_VERTEX_NORMALS%""%"Yes"%AREA_ORIENTATION%ORIENTATION_CHECK_PARAMS%"Yes"
    SUMMARY = None
    PASSED -> GeometryPropertySetter
    REPAIRED -> GeometryPropertySetter
Note: Set a counter trait on each / face for unique face id
GeometryPropertySetter
    CNT_ATTR = _count
    DOMAIN = counter
    GQUERY:
      for $geom in //geometry
      where $geom/@fme_geometry_type = 'IFMEFace'
      return number($geom/@fme_id)
    OVERWRITE_CHOICE = Yes
    SCOPE = Global
    SETTYPE_PARAM = Traits From Counter
    START = 0
    SET -> GeometryPartExtractor_4
    SET -> AppearanceSetter_3 [GEOMETRY]
Note: Extract faces from brep
GeometryPartExtractor_4
    EXTRACTTYPE_PARAM = Extract
    GQUERY:
      for $geom in //geometry
      where $geom/@fme_geometry_type = 'IFMEFace'
      return number($geom/@fme_id)
    PROCESSED -> GeometryPropertyExtractor
Note: Extract face id to attribute
GeometryPropertyExtractor
    EXTRACTTYPE_PARAM = Traits
    PREFIX_EXTRACTED_TRAITS = No
    TRAIT_ATTR_LIST = _count,No
    EXTRACTED -> GeometryPartExtractor_3
Note: Extract polygon from face
GeometryPartExtractor_3
    EXTRACTTYPE_PARAM = Extract
    GQUERY:
      for $geom in //geometry
      where $geom/@fme_geometry_type = 'IFMEPolygon'
      return number($geom/@fme_id)
    PROCESSED -> MeasureExtractor_2
Note: Get z normal of polygon
MeasureExtractor_2
    GEOM_TYPE = Individual Vertex by Index
    INDEX = 0
    MEASURE_ATTR = _normal_z
    MEASURE_NAME = fme_vertex_normal_z
    -> TestFilter_6
Note: Separate ground, roof and / wall faces by z normal value
TestFilter_6
    DEFAULT_VALUE = Wall
    TEST_LIST = "BOOL_OP,AND,COMPOSITE_TEST,""""""1"""""",TEST_CLAUSE,TEST @Value(_normal_z) <= -0.5",Ground,"BOOL_OP,OR,COMPOSITE_TEST,""""""1"""""",TEST_CLAUSE,TEST @Value(_normal_z) >= 0.1",Roof
    Ground -> AppearanceStyler_2
    Roof -> AppearanceStyler_2
    Wall -> AppearanceStyler_2
AppearanceStyler_2
    ALPHA = 1
    APPEARANCE_NAME = Ground
    DIFFUSE_COLOR = 1,0.133333,0.8
    TEXTURE_CENTER_U = 0.0
    TEXTURE_CENTER_V = 0.0
    TEXTURE_ROTATION_ANGLE = 0.0
    TEXTURE_U_OFFSET = 0.0
    TEXTURE_U_SCALING_FACTOR = 1.0
    TEXTURE_U_SHEARING_FACTOR = 0.0
    TEXTURE_V_OFFSET = 0.0
    TEXTURE_V_SCALING_FACTOR = 1.0
    TEXTURE_V_SHEARING_FACTOR = 0.0
    TEXTURE_WRAP_DISPLAY = Repeat in U and V
    -> AppearanceSetter_3 [APPEARANCE]
Note: Clearance space Visualisation
AppearanceSetter_3
    DEF_STORAGE = Create New Definitions
    GQUERY:
      for $geom in //geometry
      where $geom/@fme_geometry_type = 'IFMEFace'
      return number($geom/@fme_id)
    JOIN_ATTR = _count
    JOIN_TRAIT = _count
    SET_ON_SIDE = Front and Back Sides
    TEXTURE_MAPPING_TYPE_CHOICE = Surface Normal
    TEXTURE_U_OFFSET2 = 0.0
    TEXTURE_U_SCALE_FACTOR = 1.0
    TEXTURE_V_OFFSET2 = 0.0
    TEXTURE_V_SCALE_FACTOR = 1.0
    USE_EXISTING_TEXTURE_COORDINATES = No
    -> GeometryExtractor
Note: save underpass space for later on
GeometryExtractor
    ATTR = _geometry
    ELLIPSOID_NAME = WGS84
    GEOHASH_PRECISION_DISPLAY = ~9.3 mm (12 characters)
    ISO6709_FORMAT_CHOICE = Degrees and Decimal Degrees
    ISO6709_MAX_DECIMAL_PLACES = 5
    JSON_MAX_DIGITS = 7
    KIND_LONG = FME Binary
    LETTERING = WGS84
    LEVELS_ATTR = _levels
    MSSQL_FORMAT_CHOICE = Geometry
    OGCVERSION = 1.2
    OGC_WKT_PRECISION_DISPLAY = 64-bit
    OGEOSMS_URL_PREFIX = http://maps.google.com/?q=
    OMIT_NAMESPACES_DISPLAY = No
    PRECISION = 0
    PREFER_POLYGON_OVER_SURFACE = No
    REMOVE_GEOMETRY = No
    -> AttributeKeeper_10
AttributeKeeper_10
    CREATE_BULK_MODE_FEATURES = NO
    KEEP_ATTRS = _geometry
    -> Junction_37

Bookmark: #0 part
CSGBuilder_3
    ATTR_ACCUM_MODE = Merge
    ATTR_CONFLICT_RES = Use A
    DIFFERENCE -> CSGEvaluator_3
CSGEvaluator_3
    -> GeometryValidator_3

Bookmark: CSG operation to get cut 3D underpass in citygml model
Note: repair in case
GeometryValidator_3
    ISSUE_ATTR_NAME = _issues
    PRESETS = Custom
    REPAIR = Yes
    RULES = PLANAR_SURFACE CHECK_AREA]DO_NOT_CHECK_AREA]TOLERANCE_MODE]AUTO]TOLERANCE]0.0]ANGULAR_TOLERANCE_MODE]AUTO]ANGULAR_TOLERANCE]0.0]FME_CONTROLLER_QUERY_FILE]transformers\dependencies\geometryvalidator\PLANAR_SURFACE.fme SOLID_VOID_REPAIR  SHELL_VALIDATION FLIP_APPEARANCE_MODE]FLIP_APPEARANCES]FME_CONTROLLER_QUERY_FILE]transformers\dependencies\geometryvalidator\SHELL_VALIDATION.fme MISSING_TEXTURE_COORDINATES  SURFACE_ORIENTATION  SOLID_ORIENTATION
    SUMMARY = Detailed
    PASSED -> Junction_20
    FAILED -> Junction_20
    REPAIRED -> Junction_20
Note: Building with cut underpasses
Junction_20
    -> Junction_33

Bookmark: Define respective parts of CityGML model
Junction_33
    -> GeometryValidator_5
Note: Create surface normals
GeometryValidator_5
    MISSING_VERTEX_NORMALS = MISSING_VERTEX_NORMALS
    PRESETS = Custom
    REPAIR = Yes
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%SHELL_VALIDATION_PARAMS%"Yes"%SOLID_VOID_REPAIR%""%"Yes"%OGC_SIMPLE_CHECK%""%"No"%OGC_VALID_CHECK%OGC_VALID_PARAMS%"No"%MISSING_TEXTURE_COORDINATES%""%"Yes"%MISSING_VERTEX_NORMALS%""%"Yes"%AREA_ORIENTATION%ORIENTATION_CHECK_PARAMS%"Yes"
    SUMMARY = None
    PASSED -> GeometryPropertySetter_2
    REPAIRED -> GeometryPropertySetter_2
Note: Set a counter trait on each / face for unique face id
GeometryPropertySetter_2
    CNT_ATTR = _count
    DOMAIN = counter
    GQUERY:
      for $geom in //geometry
      where $geom/@fme_geometry_type = 'IFMEFace'
      return number($geom/@fme_id)
    OVERWRITE_CHOICE = Yes
    SCOPE = Global
    SETTYPE_PARAM = Traits From Counter
    START = 0
    SET -> GeometryPartExtractor_5
Note: Extract faces from brep
GeometryPartExtractor_5
    EXTRACTTYPE_PARAM = Extract
    GQUERY:
      for $geom in //geometry
      where $geom/@fme_geometry_type = 'IFMEFace'
      return number($geom/@fme_id)
    PROCESSED -> GeometryPropertyExtractor_2
    PROCESSED -> Counter_7
Note: Extract face id to attribute
GeometryPropertyExtractor_2
    EXTRACTTYPE_PARAM = Traits
    PREFIX_EXTRACTED_TRAITS = No
    TRAIT_ATTR_LIST = _count,No
    EXTRACTED -> GeometryPartExtractor_2
Note: Extract polygon from face
GeometryPartExtractor_2
    EXTRACTTYPE_PARAM = Extract
    GQUERY:
      for $geom in //geometry
      where $geom/@fme_geometry_type = 'IFMEPolygon'
      return number($geom/@fme_id)
    PROCESSED -> MeasureExtractor_3
Note: Get z normal of polygon
MeasureExtractor_3
    GEOM_TYPE = Individual Vertex by Index
    INDEX = 0
    MEASURE_ATTR = _normal_z
    MEASURE_NAME = fme_vertex_normal_z
    -> BoundsExtractor_4
Note: get min h of each face OuterCeilingSurf
BoundsExtractor_4
    ZMIN = minHface
    -> AttributeExposer
Note: expose minHeight as it somehow get lost
AttributeExposer
    ATTR_LIST = minHeight
    -> DefineCityGMLparts

Bookmark: recover geometry of underpass
Counter_7
    CNT_ATTR = _count
    DOMAIN = counter
    SCOPE = Local
    START = 0
    -> Tester_7
Tester_7
    BOOL_OP = OR
    COMPOSITE_TEST = 1
    TEST_CLAUSE = TEST @Value(_count) = 0
    TEST_MODE = TEST
    PASSED -> GeometryRemover_3
GeometryRemover_3
    -> GeometryReplacer_2
GeometryReplacer_2
    ELLIPSOID_NAME = WGS84
    KIND_LONG = FME Binary
    LETTERING = WGS84
    MSSQL_FORMAT_CHOICE = Geometry
    OGC_WKT_PRECISION_DISPLAY = 64-bit
    OUTPUT_POINT_DISPLAY = Point
    REMOVE_ATTRIBUTE = Yes
    SOURCE = @Value(_geometry)
    SRS_AXIS_ORDER_DISPLAY = Automatic
    -> AggregateFilter_2
AggregateFilter_2
    AGGREGATE -> Deaggregator_5
    NOT_AGGREGATE -> GeometryCoercer_7
Note: if more than 1 solid
Deaggregator_5
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> GeometryCoercer_7
GeometryCoercer_7
    GQUERY:
      for $geom in //geometry
      where $geom/count(parent::geometry) = 0
      return number($geom/@fme_id)
    KIND = fme_composite_surface
    COERCED -> Deaggregator_7
Deaggregator_7
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = Yes
    DEAGGREGATED -> GeometryCoercer_9
Note: extract outer faces out of solid
GeometryCoercer_9
    GQUERY:
      for $geom in //geometry
      where $geom/count(parent::geometry) = 0
      return number($geom/@fme_id)
    KIND = fme_polygon
    COERCED -> FaceReplacer_3

Bookmark: mark faces belonging to underpass
FaceReplacer_3
    ANGULAR_TOLERANCE_CHOICE = Ignore
    THICKNESS_TOLERANCE_CHOICE = Ignore
    -> SurfaceOnSurfaceOverlayer [SURFACE]
FaceReplacer_2
    ANGULAR_TOLERANCE_CHOICE = Ignore
    THICKNESS_TOLERANCE_CHOICE = Ignore
    -> SurfaceOnSurfaceOverlayer [SURFACE]
Note: check overlap of underpass structure with cut geometry
SurfaceOnSurfaceOverlayer
    ACCUM_ATTRS_NAME = Use Attributes From One Feature
    DEAGGREGATE_INPUT = Yes
    ENABLE_TOLERANCE = Yes
    LIST_ATTRS_TO_INCLUDE = gml_id
    LIST_NAME = inter
    NORMAL_TOLERANCE = 0.5
    OFFSET_TOLERANCE = 0.1
    OVC_ATTR = _overlaps
    SURFACE -> XORunderpass
Note: Wall/OuterCeilingSurface belongs to underpass ?
XORunderpass: Tester
    BOOL_OP = OR
    COMPOSITE_TEST = 1
    TEST_CLAUSE = TEST @Value(_overlaps) = 2
    TEST_MODE = TEST
    PASSED -> Junction_32
    FAILED -> Junction_35
Note: Set up Passage
Junction_32
    -> Junction_42
Note: to Walls & OuterCeilings
Junction_35
    -> Junction_43

Bookmark: Classifier
Note: Separate ground, roof and / wall faces by z normal value
DefineCityGMLparts: TestFilter
    DEFAULT_VALUE = Wall
    TEST_LIST:
      "BOOL_OP,AND,COMPOSITE_TEST,""""""1 AND 2"""""",TEST_CLAUSE,TEST @Value(_normal_z) <= -0.5
      TEST @Value(minHface) <= @sum(@Value(minHeight),0.2)",Ground,"BOOL_OP,OR,COMPOSITE_TEST,""""""1"""""",TEST_CLAUSE,TEST @Value(_normal_z) >= 0.1",Roof,"BOOL_OP,AND,COMPOSITE_TEST,""""""1 AND 2"""""",TEST_CLAUSE,TEST @Value(_normal_z) <= -0.5
      TEST @Value(minHface) > @sum(@Value(minHeight),0.2)",OuterCeilingSurface
    Ground -> AttributeCreator_4
    Roof -> AttributeCreator_3
    OuterCeilingSurface -> AttributeCreator_2
    Wall -> AttributeCreator
AttributeCreator_2
    ATTR_TABLE = SET_TO name = CeilingSurface
    -> FaceReplacer_2
    -> Junction_39
AttributeCreator
    ATTR_TABLE = SET_TO name = WallSurface
    -> FaceReplacer_2
    -> Junction_39
AttributeCreator_4
    ATTR_TABLE = SET_TO name = GroundSurface
    -> Junction_44
    -> Junction_39
AttributeCreator_3
    ATTR_TABLE = SET_TO name = RoofSurface
    -> Junction_44
    -> Junction_39

Bookmark: CityGML Setter
Note: Walls & Ceilings being underpass
Junction_42
    -> AttributeKeeper_9
Note: Gather all elements creating Solid representaton of building
Junction_39
    -> FaceReplacer_4
Note: Gather all Roofs, ground etc. not being checked with underpass
Junction_44
    -> AttributeExposer_2

Bookmark: new uniqueID and link to Bld
AttributeKeeper_9
    CREATE_BULK_MODE_FEATURES = NO
    KEEP_ATTRS = gml_id
    -> AttributeRenamer_3
AttributeRenamer_3
    ATTR_TABLE = RENAME_SET_DEFAULT gml_id > gml_parent_id
    -> AttributeCreator_5
AttributeCreator_5
    ATTR_TABLE = SET_TO name = BuildingInstallation
    -> AttributeCreator_6

Bookmark: Underpass-specific attributes
Note: link to code list
AttributeCreator_6
    ATTR_TABLE = SET_TO citygml_function{0}.codeSpace = http://www.sig3d.org/codelists/Handbuch-SIG3D/building/2.0/CL-V1.0/BuildingInstallation_function.xml
    -> AttributeValueMapper_2
Note: CityGML Spec.:" / Codelist (SIG3D): / BldInst CodeList
Note: set Durchfahrt function
AttributeValueMapper_2
    DEFAULT_VALUE = 9998
    DIRECTION = Forward (Source To Destination)
    LUT = BuildingInstallation,1002
    SRC = name
    VAL_ATTR = citygml_function{0}
    -> DateTimeStamper_2
Note: add time of refinement update
DateTimeStamper_2
    DATETIME_ATTR = refinementDate
    STAMP_TYPE = date
    TIMEZONE = utc
    -> Aggregator_5

Bookmark: geometry
Note: aggregate to one set
Aggregator_5
    ACCUM_ATTRS_NAME = Use Attributes From One Feature
    AGGREGATE_TYPE = Homogeneous Collection (If Possible)
    ATTR_TO_TRAIT = Yes
    ID_SELECTION = ID and Parent ID
    MODE = Geometry - Assemble One Level
    PRESERVE_ID = No
    SEP = ,
    AGGREGATE -> UUIDGenerator_3
UUIDGenerator_3
    UUID_ATTR = _uuid
    -> StringConcatenator_3
StringConcatenator_3
    ACTION = Create New Attribute
    PARM_LINE = fme_basicstring:21%1%13:@Value(gml_parent_id)_@Value(_uuid)
    VAL_ATTR = gml_id
    -> BoundsExtractor_11
CityGMLGeometrySetter_3
    GEOM = lod3Geometry
    ROLE = outerBuildingInstallation
    -> BuildingInstallation (writer CITYGML_2)

Bookmark: ClearanceMax
BoundsExtractor_11
    ZMAX = zMax
    ZMIN = zMin
    -> ExpressionEvaluator_4
ExpressionEvaluator_4
    ACTION = Create New Attribute
    EXPRESSION = @sub(@Value(zMax),@Value(zMin))
    VAL_ATTR = maxClearance
    -> AttributeRounder
Note: nn.nn
AttributeRounder
    PLACES = 2
    ROUND_TYPE = Nearest
    SRC_ATTRS = maxClearance
    -> CityGMLGeometrySetter_3

Bookmark: Walls, Roofs etc. Set corresponding attributes
Note: Walls & Ceilings not being underpass
Junction_43
    -> AttributeExposer_2
Note: expose id of a building
AttributeExposer_2
    ATTR_LIST = gml_id
    -> AttributeKeeper_6

Bookmark: Geometry Repair
FaceReplacer_4
    ANGULAR_TOLERANCE_CHOICE = Ignore
    THICKNESS_TOLERANCE_CHOICE = Ignore
    -> Aggregator_4
Aggregator_4
    ACCUM_ATTRS_NAME = Use Attributes From One Feature
    AGGREGATE_TYPE = Homogeneous Collection (If Possible)
    ATTR_TO_TRAIT = Yes
    ID_SELECTION = ID and Parent ID
    MODE = Geometry - Assemble One Level
    PRESERVE_ID = No
    SEP = ,
    AGGREGATE -> GeometryCoercer_5
GeometryCoercer_5
    GQUERY:
      for $geom in //geometry
      where $geom/count(parent::geometry) = 0
      return number($geom/@fme_id)
    KIND = fme_composite_surface
    COERCED -> Deaggregator_6
Deaggregator_6
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = Yes
    DEAGGREGATED -> GeometryPartExtractor_8
Note: deaggregate composites and merge with single faces
GeometryPartExtractor_8
    GQUERY:
      for $geom in //geometry
      where $geom/@fme_geometry_type = 'IFMECompositeSurface'
      return number($geom/@fme_id)
    EXTRACTED -> Deaggregator_8
    UNTOUCHED -> SurfaceDissolver
Deaggregator_8
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = Yes
    DEAGGREGATED -> SurfaceDissolver
SurfaceDissolver
    ACCUM_INPUT_ATTRS = Use Attributes From One Feature
    DEAGGREGATE_INPUT = Yes
    MATCHING_APPS = No
    NORMAL_TOLERANCE = 0
    OFFSET_TOLERANCE = 0
    SEPARATE_SURFACES = No
    SURFACE -> Aggregator_3
Aggregator_3
    ACCUM_ATTRS_NAME = Use Attributes From One Feature
    AGGREGATE_TYPE = Homogeneous Collection (If Possible)
    ATTR_TO_TRAIT = Yes
    ID_SELECTION = ID and Parent ID
    MODE = Geometry - Assemble One Level
    PRESERVE_ID = No
    SEP = ,
    AGGREGATE -> GeometryCoercer_6
GeometryCoercer_6
    GQUERY:
      for $geom in //geometry
      where $geom/count(parent::geometry) = 0
      return number($geom/@fme_id)
    KIND = fme_composite_surface
    COERCED -> AttributeExposer_3

Bookmark: Respective geometry and others
Note: add time of refinement update
DateTimeStamper
    DATETIME_ATTR = refinementDate
    STAMP_TYPE = date
    TIMEZONE = utc
    -> VolumeCalculator_2
Note: add new volume
VolumeCalculator_2
    MULT = 1
    SET_TRAIT = No
    VOLUME_ATTR = volume
    -> CityGMLGeometrySetter
Note: set building
CityGMLGeometrySetter
    GEOM = lod3Solid
    ROLE = cityObjectMember
    -> Building (writer CITYGML_2)

Bookmark: new uniqueID and link to Bld
Note: only name and id
AttributeKeeper_6
    CREATE_BULK_MODE_FEATURES = NO
    KEEP_ATTRS = name,gml_id
    -> AttributeRenamer_2
AttributeRenamer_2
    ATTR_TABLE = RENAME_SET_DEFAULT gml_id > gml_parent_id
    -> UUIDGenerator
UUIDGenerator
    UUID_ATTR = _uuid
    -> StringConcatenator
StringConcatenator
    ACTION = Create New Attribute
    PARM_LINE = fme_basicstring:21%1%13:@Value(gml_parent_id)_@Value(_uuid)
    VAL_ATTR = gml_id
    -> AttributeKeeper_8

Bookmark: Respective geometry and others
AttributeKeeper_8
    CREATE_BULK_MODE_FEATURES = NO
    KEEP_ATTRS = gml_id,gml_parent_id,name
    -> CityGMLGeometrySetter_2
Note: set building
CityGMLGeometrySetter_2
    GEOM = lod3MultiSurface
    ROLE = boundedBy
    -> CityGMLSemSetter
CityGMLSemSetter: TestFilter
    DEFAULT_VALUE = <UNFILTERED>
    TEST_LIST = "BOOL_OP,OR,COMPOSITE_TEST,""""""1"""""",TEST_CLAUSE,TEST @Value(name) = GroundSurface",GroundSurface,"BOOL_OP,OR,COMPOSITE_TEST,""""""1"""""",TEST_CLAUSE,TEST @Value(name) = RoofSurface",RoofSurface,"BOOL_OP,OR,COMPOSITE_TEST,""""""1"""""",TEST_CLAUSE,TEST @Value(name) = WallSurface",WallSurface,"BOOL_OP,OR,COMPOSITE_TEST,""""""1"""""",TEST_CLAUSE,TEST @Value(name) = CeilingSurface",CeilingSurface
    GroundSurface -> GroundSurface (writer CITYGML_2)
    RoofSurface -> RoofSurface (writer CITYGML_2)
    WallSurface -> WallSurface (writer CITYGML_2)
    CeilingSurface -> CeilingSurface (writer CITYGML_2)

FME custom transformer SolidDissolver
The SolidDissolver dissolves adjoining solids into a single feature. Any non-solid geometries will be output untouched through the <Rejected> port.
The SolidDissolver has the following parameters:
    Group By
If you do not select Group By attributes, then all features fall into the same group.
When you select Group By attributes, this transformer will dissolve the geometries of the input solid features, based on the selection in the Group By parameter. Each group of features that have the same values for the Group By attributes will be processed independently of other groups.
    Count Attribute
If a Count Attribute is entered, then an attribute with this name will be added to each output solid, containing the number of features that resulted in the output solid.
    Keep Input Attributes
If Keep Input Attributes is set to Yes, the attributes from the original features will be merged onto the output Dissolved features.
    List Name
If a List Name is specified, then all attributes of an input feature will be stored as part of a list attribute entry in the output Dissolved feature.
    Attributes to Concatenate
Attributes can be concatenated so that the resulting Dissolved feature preserves multiple source attribute values under the same attribute name. For example, if input feature 1 has an id attribute of 1 and input feature 2 has an id attribute of 2, specifying id for this parameter together with a separate character of , will cause the output Dissolved feature to have an id with value 1, 2.
    Separator Character
The Separator Character is used to separate elements within an attribute value string. For example, if features with attribute values of 'River Rd', 'Marine Dr' and 'HWY 1' for the attribute named 'Road Name' respectively, and the Separator Character is , (a comma followed by a space) on the output solid feature, the attribute 'Road Name' will contain 'River Rd, Marine Dr, HWY 1' as a value.
The separator character can be expressed as a regular character but it can also contain special characters beginning with a backslash ("\"), as specified in the following table.
If the sequence is not listed in the table, the backslash character is ignored. (For example, entering lan\es will be interpreted as lanes.) If no separator character is supplied, attributes will be concatenated without a separator.
    Sequence
    Description
\a Audible alert (bell) (0x07)
\b Backspace (0x08)
\f Form feed (0x0c)
\n Newline (0x0a)
\r Carriage return (0x0d)
\t Tab (0x09)
\v Vertical tab (0x0b)
\\ Backslash
(Note: A single backslash entered at the end of a value will be converted to an escaped backslash.)
    Attributes to Sum
Any attributes specified in this field will undergo statistical accumulation.
For example, if two input solids have an attribute 'salary' set to 30000 and 50000, then summing them would result in a 'salary' of 80000 on the dissolved output.
    Attributes to Average
Any attributes specified in this field will undergo statistical accumulation.
For example, if two input solids have an attribute 'salary' set to 30000 and 50000, then averaging them would result in a 'salary' of 40000 on the dissolved output.

Parameters:
- GROUP_BY =   # " " Group By
- COUNT_ATTR =   # TYPE:varchar(200) Count Attribute
- ACCUM_ATTRS_NAME = No   # Keep Input Attributes
- LIST_NAME =   # List Name
- CONCAT_ATTRS =   # " " Attributes to Concatenate
- SEP = ,   # Separator Character
- SUM =   # " " Attributes to Sum
- AV =   # " " Attributes to Average

Note: Refine geometry / to get all solids
GeometryRefiner
    -> AttributeExposer
Note: Expose for later removal
AttributeExposer
    ATTR_LIST = pyfme_none,pyfme_list{}
    -> GeometryFilter
Note: Force to brep solids
GeometryCoercer
    GQUERY:
      for $geom in //geometry
      where $geom/count(parent::geometry) = 0
      return number($geom/@fme_id)
    KIND = fme_brep_solid
    COERCED -> Aggregator
    UNTOUCHED -> Aggregator
Note: Aggregate solids
Aggregator
    ACCUM_ATTRS_NAME = $(ACCUM_ATTRS_NAME)
    AGGREGATE_TYPE = Homogeneous Collection (If Possible)
    AV = $(AV)
    CONCAT_ATTRS = $(CONCAT_ATTRS)
    COUNT_ATTR = $(COUNT_ATTR)
    GROUP_BY = $(GROUP_BY)
    LIST_NAME = $(LIST_NAME)
    MODE = Geometry - Assemble One Level
    ORDERED = No
    SEP = $(SEP)
    SUM = $(SUM)
    AGGREGATE -> BoundsExtractor
    AGGREGATE -> Clipper [CLIPPER]
Dissolved (output)

Bookmark: Input Data
Solids (input)
    -> GeometryRefiner

Bookmark: Filter out solids
GeometryFilter
    BREAK_AGG = No
    GEOM_PORT_NAMES = Point Line Arc Area Ellipse Text Raster "Point Cloud" Surface Solid Collection Null Instance
    POINT -> <Rejected> (output)
    LINE -> <Rejected> (output)
    ARC -> <Rejected> (output)
    AREA -> <Rejected> (output)
    ELLIPSE -> <Rejected> (output)
    TEXT -> <Rejected> (output)
    RASTER -> <Rejected> (output)
    POINTCLOUD -> <Rejected> (output)
    SURFACE -> <Rejected> (output)
    SOLID -> GeometryCoercer
    COLLECTION -> <Rejected> (output)
    NULL -> <Rejected> (output)
    INSTANCE -> <Rejected> (output)

Bookmark: Create bounding cube of aggregate
Note: Extract bounds
BoundsExtractor
    XMAX = _xmax
    XMIN = _xmin
    YMAX = _ymax
    YMIN = _ymin
    ZMAX = _zmax
    ZMIN = _zmin
    -> 2DBoxReplacer
Note: Replace by / bounding rectangle
2DBoxReplacer
    MAXXVALATTR = @Value(_xmax)
    MAXYVALATTR = @Value(_ymax)
    MINXVALATTR = @Value(_xmin)
    MINYVALATTR = @Value(_ymin)
    BOX -> 3DForcer
Note: Elevate bounding / rectangle by min z
3DForcer
    KEEPZVAL = No
    ZVALATTR = @Value(_zmin)
    -> Extruder_2
Note: Extrude to max z
Extruder_2
    EXTRUSION_HEIGHT = @Value(_zmax)-@Value(_zmin)
    EXTRUSION_VECTOR_INPUT = Height
    -> Clipper [CLIPPEE]

Bookmark: Clip and clean attributes
Note: Clip bounding cube by / aggregated solids to / create dissolved solid
Clipper
    BOUNDARY_CASES = Treat as Inside
    CLIP_TYPE = Single Clipper
    CONNECT_Z_MODE = First Wins
    CREATE_AGGREGATES = Yes
    LINES_AS_SEGMENTS = No
    PRESERVE_CLIPPEE_EXTENTS = No
    INSIDE -> AttributeRemover
Note: Remove temp attributes
AttributeRemover
    LIST_ATTRS = pyfme_list{}
    REMOVE_ATTRS = pyfme_none,_xmax,_xmin,_ymax,_ymin,_zmax,_zmin
    -> Dissolved (output)

Bookmark: Rejected features ignored
<Rejected> (output)
